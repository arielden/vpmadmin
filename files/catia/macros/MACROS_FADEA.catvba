Attribute VB_Name = "A1_Guardar"
'AUTOR: SEBASTIAN ASSAIN
'NOMBRE: A1_Guardar
'VERSION 1.4
'FECHA: 22/04/2019
'CAMBIOS:   RECONOCE ENTRE UNA INSTANCIA Y UNA PARTE, RECONOCE NUMERACION DE PROYECTO F50
'           RECONOCE P/N ASIGNADOS POR LA SUBRUTINA "CAMBAIR P/N" CON EL OBJETIVO DE CAMBIAR EL P/N
'FRASE: LAS SOCIEDADES QUE PROGRESAN SON AQUELLAS EN LAS QUE UN ADULTO PLANTA UN ÁRBOL SABIENDO QUE JAMÁS LLEGARÁ A DISFRUTAR SU SOMBRA.
'DESCRIPCIÓN: GUARDA PARTES O PRODUCTOS EN CARPETAS ACORDE AL P/N IDICADO

Sub CATMain()

Dim Grupo As Variant
Dim Archivo_Existente As Variant
Dim Ruta As String
Dim RUTA_SALIDA As String
Dim Nombre_Ruta As String
Dim Nombre_Ruta_Archivo_Guardado As String
Dim Nombre_Ruta_Aux As String
Dim Nombre_Archivo As String
Dim Reemplazo As VbMsgBoxResult
Dim Armonizado As VbMsgBoxResult
Dim Tipo_Archivo As String
Dim Nom_PartProd As String
Dim producto As Product
Dim relationsproducto1 As Relations
Dim productDocument1 As ProductDocument
Dim product1 As Product
Dim partDocument1 As PartDocument
Dim part1 As Part
Dim relationsparte1 As Relations
Dim oseleccion As Selection
Dim Instancia As String
Dim Instancia_sp As String
Dim NInst As Variant
Dim NInst_Nueva As Variant
Dim retro As Integer
Dim BuscaPunto As String
Dim InstVec() As Variant
Dim NInstVec() As Variant
Dim Cambio As Boolean
Dim BodyToRename As Body

'SI NO EXISTE NINGUN DOCUMENTO ABIERTO SE EVITA QUE LA MACRO DEVUELVA UN ERROR
'=============================================================================
If CATIA.Documents.Count = 0 Or CATIA.Windows.Count = 0 Then
    MsgBox "Debe tener abierto al menos un documento para utilizar esta herramienta", vbCritical
    Exit Sub
End If

Call PROYECTO(PROY_CODE, PROYS, ARM_SYS)

'APAGA TODA LA GEOMETRIA (EXCEPTO OUTPUTS DE GEOMETRICAL SETS)
'============================================================
'Set productDocument1 = CATIA.ActiveDocument
'Set selection1 = productDocument1.Selection
'selection1.Search "CATGmoSearch.OpenBodyFeature, sel"
'selection1.Search "(CATPrtSearch.AxisSystem.Visibility=Visible + (CATPrtSearch.Surface.Visibility=Visible + (CATPrtSearch.Wireframe.Visibility=Visible + CATPrtSearch.Sketch.Visibility=Visible))),all"
'Set VisPropSet1 = selection1.VisProperties
'VisPropSet1.SetShow catVisPropertyNoShowAttr


'SI SOLAMENTE TENEMOS ABIERTA UNA PARTE, SE SALTA EL CAMBIO DE NOMBRE DE INSTANCIAS
'=================================================================================
If UCase(TypeName(CATIA.ActiveDocument)) = UCase("ProductDocument") Then

    CATIA.ActiveDocument.Product.ApplyWorkMode DESIGN_MODE
    
    'REFERENCIAS PARA REVISAR TODOS LOS COMPONENTES DEL PRODUCTO
    '===========================================================
    Dim oTopProductDoc As ProductDocument
    Dim oTopProduct As Product
    Dim INumberOfItems As Long
    Dim m As Integer
    
    'SE BUSCAN PARTES CON EL MISMO NOMBRE DENTRO DEL PRODUCTO
    '========================================================
    Set oTopProductDoc = CATIA.ActiveDocument
    Set oTopProduct = oTopProductDoc.Product
    
    INumberOfItems = oTopProduct.Products.Count
    
    NInst_Nueva = 1
        
    ReDim InstVec(INumberOfItems)
    ReDim NInstVec(INumberOfItems)
        
        'SE OBTIENEN TODOS LOS NOMBRES Y NUMEROS DE INSTANCIA DEL PRODUCTO
        '=================================================================
        For k = 1 To INumberOfItems
            On Error Resume Next
            retro = 0
            
            Do
                retro = retro + 1
                Instancia = Right(oTopProduct.Products.ITEM(k).Name, retro) 'n° instancia
                InstVec(k) = Mid(oTopProduct.Products.ITEM(k).Name, 1, Len(oTopProduct.Products.ITEM(k).Name) - retro)
                BuscaPunto = Left(Instancia, 1)
                'NInstVec(k) = Right(Instancia, retro - 1)
                NInstVec(k) = "0"
                    'SI HAY UN ERROR EN EL FORMATO N EL QUE ESTA ESCRITA LA INSTANCIA SALE AVISANDO DE QUÉ INSTANCIA SE TRATA
                    '========================================================================================================
                    If Err.Number <> 0 Then
                        MsgBox "Atención!! Se recorrió todo el árbol." & vbNewLine & vbNewLine & "El PN: " & _
                        oTopProduct.Products.ITEM(k).ReferenceProduct.Name & " tiene uno de los siguientes problemas:" _
                        & vbNewLine & vbNewLine & "(1) La instancia no cumple con el formato de instancia regular de CATIA" _
                        & vbNewLine & "Corrija este elemento a la brevedad para evitar futuros errores.", vbCritical + vbOKOnly
                        Exit Sub
                    End If
            Loop While BuscaPunto <> "."
            
        '    MsgBox "--" & oTopProduct.Products.Item(k).ReferenceProduct.Name
            
            'SE EL NUMERO DE PARTE A TODOS LAS INSTANCIAS GUARDADAS EN LOS VECTORES
            '======================================================================
            Cambio = False
            If InstVec(k) <> oTopProduct.Products.ITEM(k).ReferenceProduct.Name Then
                oTopProduct.Products.ITEM(k).Name = k
                InstVec(k) = oTopProduct.Products.ITEM(k).ReferenceProduct.Name
                Cambio = True
            End If
            
            For m = 1 To k
                If InstVec(k) = oTopProduct.Products.ITEM(m).ReferenceProduct.Name Then
                    NInstVec(k) = NInstVec(k) + 1
                End If
            Next
        
            If Cambio = True Then
            oTopProduct.Products.ITEM(k).Name = InstVec(k) & "." & NInstVec(k)
            End If
        
            On Error GoTo 0
        Next 'k
   
End If
    
'PUNTO DE CONTROL -COMIENZO DE GUARDADO-

Call Rutas("PROCESO", RUTA_SALIDA, PROY_CODE)

Set oseleccion = CATIA.ActiveDocument.Selection
'MsgBox oSeleccion.Count

'NUMEROS ENTEROS PARA TRABAJAR CON PART NUMBERS
'==============================================
Call Param_PN(ARR_PN, PROY_CODE)
intgr_N_PN = ARR_PN(1)
intgr_POS_GRUPO = ARR_PN(2)
intgr_TIPO_PN = ARR_PN(3)
intgr_LONG_TIPO = ARR_PN(4)
str_PROD_MAX = ARR_PN(6)
str_PROD_MIN = ARR_PN(7)
'==============================================

'SI HAY ALGO SELECCIONADO
'========================
If oseleccion.Count > 0 Then

    'LOOP DESDE 1 HASTA LOS ELEMENTOS SELECCIONADOS
    '==============================================
    For i = 1 To oseleccion.Count
    
        'SI EL TIPO DE DOCUMENTO ES UN PRODUCTO
        '======================================
        If UCase(TypeName(oseleccion.ITEM(i).Value)) = UCase("Product") Then
            
            '=========================================================================================================================================================================
            'SI EL DOCUMENTO GUARDADO DENTRO DEL PRODUCTO ES UNA PARTE
            '=========================================================================================================================================================================
            If UCase(TypeName(oseleccion.ITEM(i).Value.ReferenceProduct.Parent)) = UCase("PartDocument") Then
                
                Set part1 = oseleccion.ITEM(i).Value.ReferenceProduct.Parent.Part
                
                If UCase(part1.Name) = UCase("SELECCIONAR_") Then
                    MsgBox "Debe seleccionar un P/N para guardar." & vbNewLine & vbNewLine & "Hágalo y vuelva a intentarlo.", vbCritical
                    Exit Sub
                End If

                Set relationsparte1 = part1.Relations
                            
                Set BodyToRename = oseleccion.ITEM(i).Value.ReferenceProduct.Parent.Part.Bodies.ITEM(1)

                PNPB = Left(oseleccion.ITEM(i).Value.ReferenceProduct.Parent.Part.Name, intgr_N_PN)

                Grupo = Mid(part1.Name, intgr_POS_GRUPO, 1)
                
                Ruta = RUTA_SALIDA & Grupo & "00\3D\"
                
                Nombre_Ruta = Ruta & part1.Name
                         
                Nombre_Archivo = Mid(oseleccion.ITEM(i).Value.ReferenceProduct.Parent.Name, 1, InStr(1, oseleccion.ITEM(i).Value.ReferenceProduct.Parent.Name, ".CATPart") - 1)
                    
                Nombre_Ruta_Archivo_Guardado = oseleccion.ITEM(i).Value.ReferenceProduct.Parent.FullName
                
                Archivo_Existente = CATIA.FileSystem.FileExists(Nombre_Ruta & ".CATPart")
                
                Archivo_Existente_Previo = CATIA.FileSystem.FileExists(Nombre_Ruta_Archivo_Guardado)
                                
                Nombre_Cambio = Ruta & part1.Name & "_CAMBIO" & ".CATPart"
                
                Cambiar = Right(Nombre_Ruta_Archivo_Guardado, Len("_CAMBIO.CATPart"))
                
                '1 - SI EL NOMBRE DE LA PARTE NO COINCIDE CON EL NOMBRE DEL ARCHIVO SE SALE DE LA SUBRUTINA Y SE PIDE SINCRONIZAR LA PARTE -SE DECIDIÓ NO PERMITIR GUARDAR PARTES NO SINCRONIZADAS, NO ES INDISPENSABLE-
                '===================================================================================================================================================================================================
                If UCase(Nombre_Archivo) <> UCase(part1.Name) And Archivo_Existente_Previo = True And UCase(Cambiar) <> UCase("_CAMBIO.CATPart") Then
                    MsgBox "Se debe sincronizar la parte antes de guardarla (1)" & vbNewLine & "Los siguientes items deben llamarse de la misma manera:" _
                    & vbNewLine & vbNewLine & "(1) Columna Excel 'Part Number Catia' = P/N_DESCRIPCION" & vbNewLine & "(2) Archivo en Windows = P/N_DESCRIPCION" _
                    & vbNewLine & "(3) 'Part Number' en CATIA = P/N_DESCRIPCION" _
                    , vbCritical, "[1] Problema de sincronización! " & part1.Name
                    'MsgBox Nombre_Archivo & " -- " & part1.Name
                    Exit Sub
                ElseIf UCase(Nombre_Archivo) <> UCase(part1.Name) And Archivo_Existente_Previo = True And UCase(Cambiar) = UCase("_CAMBIO.CATPart") Then
                    
                    On Error Resume Next
                    Err.Clear
                    CATIA.StartCommand ("Clear History")
                    oseleccion.ITEM(i).Value.ReferenceProduct.Parent.SaveAs (Nombre_Ruta)
                    
                    'SI HAY UN ERROR EN EL GUARDADO EVITA BORRAR EL ARCHIVO ORIGINAL
                    '================================================================
                    Mata = True
                    If Err.Number <> 0 Then
                        Mata = False
                    End If
                    
                    If Mata = True Then
                        BodyToRename.Name = PNPB
                        Kill (Nombre_Ruta_Archivo_Guardado)
                        Exit Sub
                    Else
                        MsgBox "La parte no ha podido guardarse debido a que usted no ha aceptado las condiciones de la ventana previa." _
                        & vbNewLine & vbNewLine & "Vuelva a intentarlo.", vbCritical
                        Exit Sub
                    End If
                    On Error GoTo 0
                
                End If
                
                    If Archivo_Existente = False Or UCase(Ruta) <> UCase(oseleccion.ITEM(i).Value.ReferenceProduct.Parent.Path) & "\" Then
                        
                        'SI EL ARCHIVO NO EXISTE PERO EN LA SESION DE CATIA TIENE ASIGNADA UNA
                        'RUTA SIGNIFICA QUE HA SIDO BORRADO SE PREGUNTA SI SE LO QUIERE VOLVER A GUARDAR
                        '===============================================================================
                        If Archivo_Existente = False And UCase(Ruta) = UCase(oseleccion.ITEM(i).Value.ReferenceProduct.Parent.Path) & "\" Then
                            Reemplazo = MsgBox("(1) El archivo:" & vbCrLf & " '" & Nombre_Ruta & "' " & "ya no existe. " & vbCrLf & vbCrLf & "Desea volver a crearlo?", vbOKCancel + vbCritical, "Atención!!")
                            If Reemplazo = vbOK Then
                                BodyToRename.Name = PNPB
                                CATIA.StartCommand ("Clear History")
                                oseleccion.ITEM(i).Value.ReferenceProduct.Parent.SaveAs (Nombre_Ruta)
                                Exit Sub
                            ElseIf Reemplazo = vbCancel Then
                                MsgBox "El archivo no fue guardado", vbCritical, "Atención! " & part1.Name
                                Exit Sub
                            End If
                        Else
                            'SE CAMBIA EL NOMBRE DE LA TABLA DE DISEŃO PARA QUE COINCIDA CON LA PARTE -ESTO ES SUMAMENTE IMPORTANTE PARA QUE FUNCIONE LA SUBRUTINA DE ARMONIZACION-
                            '======================================================================================================================================================

                        End If
                    
                    End If
                          
                        'SI EL ARCHIVO YA TIENE UNA RUTA
                        '===============================
                        If UCase(Ruta) = UCase(oseleccion.ITEM(i).Value.ReferenceProduct.Parent.Path) & "\" Then
                            BodyToRename.Name = PNPB
                            oseleccion.ITEM(i).Value.ReferenceProduct.Parent.Save
                        
                        'SI EL ARCHIVO NO TIENE UNA NOMBRE O TIENE UNA QUE NO COINCIDE CON LA RUTA CORRECTA
                        '==================================================================================
                        ElseIf oseleccion.ITEM(i).Value.ReferenceProduct.Parent.FullName = "" Or UCase(Ruta) <> UCase(oseleccion.ITEM(i).Value.ReferenceProduct.Parent.Path) & "\" Then
                            If Archivo_Existente = True Then
                            Reemplazo = MsgBox("El archivo ya se encuentra creado, desea reemplazarlo?", vbOKCancel, "Atención!! " & part1.Name)
                                If Reemplazo = vbOK Then
                                    BodyToRename.Name = PNPB
                                    Nombre_Ruta_Aux = Nombre_Ruta & ".CATPart"
                                    CATIA.StartCommand ("Clear History")
                                    oseleccion.ITEM(i).Value.ReferenceProduct.Parent.SaveAs (Nombre_Ruta_Aux)
                                    'Exit Sub
                                ElseIf Reemplazo = vbCancel Then
                                    MsgBox "El archivo no fue guardado", vbCritical, "Atención! " & part1.Name
                                    Exit Sub
                                End If
                            ElseIf Archivo_Existente = False Then
                                BodyToRename.Name = PNPB
                                CATIA.StartCommand ("Clear History")
                                oseleccion.ITEM(i).Value.ReferenceProduct.Parent.SaveAs (Nombre_Ruta)
                            End If
                        
                        'SI EXISTE OTRO CASO SE DEBE REVISAR POR EL PROGRAMADOR
                        '======================================================
                        Else
                        MsgBox "Programacion en construcción" & part1.Name
                        End If
                        
'                End If
            
            '=========================================================================================================================================================================
            'SI EL DOCUMENTO GUARDADO DENTRO DE UN PRODUCTO ES UN PRODUCTO
            '=========================================================================================================================================================================
            ElseIf UCase(TypeName(oseleccion.ITEM(i).Value.ReferenceProduct.Parent)) = UCase("ProductDocument") Then
            'MsgBox i & "_entro_Producto"
                                                 
                Set producto = oseleccion.ITEM(i).Value.ReferenceProduct.Parent.Product
                
'                If UCase(producto.Name) = UCase("SELECCIONAR_") Then
'                    MsgBox "Debe seleccionar un P/N para guardar." & vbNewLine & vbNewLine & "Hágalo y vuelva a intentarlo.", vbCritical
'                    Exit Sub
'                End If
                
                Set relationsproducto1 = producto.Relations

                Grupo = Mid(producto.Name, intgr_POS_GRUPO, 1)
                
                Ruta = RUTA_SALIDA & Grupo & "00\3D\"
            
                Nombre_Ruta = Ruta & producto.Name
                   
                Nombre_Archivo = Mid(oseleccion.ITEM(i).Value.ReferenceProduct.Parent.Name, 1, InStr(1, oseleccion.ITEM(i).Value.ReferenceProduct.Parent.Name, ".CATProduct") - 1)
                
                Nombre_Ruta_Archivo_Guardado = oseleccion.ITEM(i).Value.ReferenceProduct.Parent.FullName
                
                Archivo_Existente = CATIA.FileSystem.FileExists(Nombre_Ruta & ".CATProduct")
                
                Archivo_Existente_Previo = CATIA.FileSystem.FileExists(Nombre_Ruta_Archivo_Guardado)
                
                Instancia = Right(oseleccion.ITEM(i).Value.Name, 2)
                
                Nombre_Cambio = Ruta & producto.Name & "_CAMBIO" & ".CATProduct"
                
                'Si el archivo esta guardado y termina en "_CAMBIO.CATProduct"
                Cambiar = Right(Nombre_Ruta_Archivo_Guardado, Len("_CAMBIO.CATProduct"))
                
                    '2 - SI EL NOMBRE DEL PRODUCTO NO COINCIDE CON EL NOMBRE DEL ARCHIVO SE SALE DE LA SUBRUTINA Y SE
                    'PIDE SINCRONIZAR LA PARTE -SE DECIDIÓ NO PERMITIR GUARDAR PARTES NO SINCRONIZADAS, NO ES INDISPENSABLE-
                    '=======================================================================================================
                    If UCase(Nombre_Archivo) <> UCase(producto.Name) And Archivo_Existente_Previo = True And UCase(Cambiar) <> UCase("_CAMBIO.CATProduct") Then
                        MsgBox "Se debe sincronizar la parte antes de guardarla (1)" & vbNewLine & "Los siguientes items deben llamarse de la misma manera:" _
                        & vbNewLine & vbNewLine & "(1) Columna Excel 'Part Number Catia' = P/N_DESCRIPCION" & vbNewLine & "(2) Archivo en Windows = P/N_DESCRIPCION" _
                        & vbNewLine & "(3) 'Part Number' en CATIA = P/N_DESCRIPCION" _
                        , vbCritical, "[2] Problema de sincronización! " & producto.Name
                        'MsgBox Nombre_Archivo & " -- " & part1.Name
                        Exit Sub
                    ElseIf UCase(Nombre_Archivo) <> UCase(producto.Name) And Archivo_Existente_Previo = True And UCase(Cambiar) = UCase("_CAMBIO.CATProduct") Then
                        
                        On Error Resume Next
                        Err.Clear
                        CATIA.StartCommand ("Clear History")
                        oseleccion.ITEM(i).Value.ReferenceProduct.Parent.SaveAs (Nombre_Ruta)
                        
                        'SI HAY UN ERROR EN EL GUARDADO EVITA BORRAR EL ARCHIVO ORIGINAL
                        '================================================================
                        Mata = True
                        If Err.Number <> 0 Then
                            Mata = False
                        End If
                        
                        If Mata = True Then
                            Kill (Nombre_Ruta_Archivo_Guardado)
                            Exit Sub
                        Else
                            MsgBox "La parte no ha podido guardarse debido a que usted no ha aceptado las condiciones de la ventana previa." _
                            & vbNewLine & vbNewLine & "Vuelva a intentarlo.", vbCritical
                            Exit Sub
                        End If
                        On Error GoTo 0
                    
                    End If
                
                    'SE EXTRAE EL NOMBRE DE LA INSTANCIA SIN CONTAR LOS DOS ULTIMOS CARACTERES
                    '=========================================================================
                    NombreInstancia = Mid(oseleccion.ITEM(i).Value.Name, 1, Len(oseleccion.ITEM(i).Value.Name) - 2)
                                    
                
                If Archivo_Existente = False Or UCase(Ruta) <> UCase(oseleccion.ITEM(i).Value.ReferenceProduct.Parent.Path) & "\" Then
                    
                    'SI EL ARCHIVO NO EXISTE PERO EN LA SESION DE CATIA TEIENE ASIGNADA UNA
                    'RUTA SIGNIFICA QUE HA SIDO BORRADO SE PREGUNTA SI SE LO QUIERE VOLVER A GUARDAR
                    '===============================================================================
                    If Archivo_Existente = False And UCase(Ruta) = UCase(oseleccion.ITEM(i).Value.ReferenceProduct.Parent.Path) & "\" Then
                        Reemplazo = MsgBox("(2) El archivo:" & vbCrLf & " '" & Nombre_Ruta & "' " & "ya no existe. " & vbCrLf & vbCrLf & "Desea volver a crearlo?", vbOKCancel + vbCritical, "Atención!!")
                        If Reemplazo = vbOK Then
                            CATIA.StartCommand ("Clear History")
                            oseleccion.ITEM(i).Value.ReferenceProduct.Parent.SaveAs (Nombre_Ruta)
                            Exit Sub
                        ElseIf Reemplazo = vbCancel Then
                            MsgBox "El archivo NO fue guardado", vbCritical, "Atención! " & producto.Name
                            Exit Sub
                        End If
                    Else

                    End If
                End If
               
                        'SE EXTRAE LA ULTIMA LETRA DEL PART NUMBER (SIN LA DESCRIPCIÓN)
                        '==============================================================
                        Nomenc_PartProd = Mid(producto.Name, intgr_TIPO_PN, intgr_LONG_TIPO)

                        'SI EL ARCHIVO YA TIENE UNA RUTA
                        '===============================
                        If UCase(Ruta) = UCase(oseleccion.ITEM(i).Value.ReferenceProduct.Parent.Path) & "\" Then
                            oseleccion.ITEM(i).Value.ReferenceProduct.Parent.Save '===========================================================================> SE GUARDA EL ARCHIVO
                        
                        'SI EL ARCHIVO NO TIENE UNA RUTA O TIENE UNA QUE NO COINCIDE CON LA RUTA CORRECTA
                        '================================================================================
                        ElseIf oseleccion.ITEM(i).Value.ReferenceProduct.Parent.FullName = "" Or UCase(Ruta) <> UCase(oseleccion.ITEM(i).Value.ReferenceProduct.Parent.Path) & "\" Then
                            
                        'SI LA NOMENCLATURA DEL PRODUCTO NO ES LA ADECUADA ESTA CONDICION LO INFORMA
                        '===========================================================================
                        If CInt(Nomenc_PartProd) < CInt(str_PROD_MIN) Or CInt(Nomenc_PartProd) > CInt(str_PROD_MAX) Then
                            Armonizado = MsgBox("Usted está por guardar un Producto con numero de parte de una Parte, desea continuar?", vbOKCancel, "Atención!" & producto.Name)
                            If Armonizado = vbOK Then
                                'SI DECIDE GUARDAR DE IGUAL MANERA, SE PERMITE
                            ElseIf Armonizado = vbCancel Then
                                MsgBox "El archivo NO fue guardado", vbCritical, "Producto como Parte! " & producto.Name
                                Exit Sub
                            End If
                        End If
                    
                    If Archivo_Existente = True Then '================================================================================================> SI EL ARCHIVO EXISTE
                    Reemplazo = MsgBox("El archivo ya se encuentra creado, desea reemplazarlo?", vbOKCancel, "Atención!! " & producto.Name) '=========> SE CONSULTA SI SE DESEA REEMPLAZARLO
                        If Reemplazo = vbOK Then '====================================================================================================> SI EL USUARIO DECIDE REEMPLAZARLO
                            CATIA.StartCommand ("Clear History")
                            oseleccion.ITEM(i).Value.ReferenceProduct.Parent.SaveAs (Nombre_Ruta) '===================================================> SE "GUARDA COMO" CON EL NOMBRE DE RUTA ASIGNADO
                            'Exit Sub
                        ElseIf Reemplazo = vbCancel Then '============================================================================================> SI EL USUARIO DECIDE CANCELAR EL REEMPLAZO
                            MsgBox "El archivo NO fue guardado", vbCritical, "Atención! " & producto.Name '===========================================> SE ADVIERTE QUE EL ARCHIVO NO SE GUARDÓ
                            Exit Sub
                        End If
                    ElseIf Archivo_Existente = False Then '===========================================================================================> SI EL ARCHIVO NO EXISTE
                        CATIA.StartCommand ("Clear History")
                        oseleccion.ITEM(i).Value.ReferenceProduct.Parent.SaveAs (Nombre_Ruta) '===========================================================> SE "GUARDA COMO" CON EL NOMBRE DE RUTA ASIGNADO
                    End If
                

                'SI EXISTE OTRO CASO SE DEBE REVISAR POR EL PROGRAMADOR
                '======================================================
                Else
                    MsgBox "Programacion en construcción" & producto.Name
                End If
            
            End If
        
        ElseIf UCase(TypeName(oseleccion.ITEM(i).Value)) = UCase("Part") Then
        
        MsgBox "Usted a selecionado una parte, debe seleccionar la instancia!" & vbCrLf & " El archivo NO se guardará", vbCritical, "Atencion!!"
        
        End If
    
    Next

Else
    'Se verifica el tipo de archivo que esta abierto
    Tipo_Archivo = TypeName(CATIA.ActiveDocument)
    
    '=====================================================================================================================================================================
    'SI EL ARCHIVO ES UN PRODUCTO
    '=====================================================================================================================================================================
    If UCase(Tipo_Archivo) = UCase("ProductDocument") And oseleccion.Count = 0 Then
    
        MsgBox "Seleccione al menos una parte o un producto. Efecto Z-Buffer (visulización) activado/desactivado.", vbCritical
        
        Set mySettingControllers = CATIA.SettingControllers

        Set MyVisSetting = mySettingControllers.ITEM("CATVizVisualizationSettingCtrl")

        'MsgBox MyVisSetting.AllZBufferElementMode

            If MyVisSetting.AllZBufferElementMode Then
                MyVisSetting.AllZBufferElementMode = False
            Else
                MyVisSetting.AllZBufferElementMode = True
            End If
        
        Exit Sub
        
    '=====================================================================================================================================================================
    'SI EL ARCHIVO ES UNA PARTE
    '=====================================================================================================================================================================
    ElseIf UCase(Tipo_Archivo) = UCase("PartDocument") Then
    
        Set partDocument1 = CATIA.ActiveDocument
        
        Set part1 = partDocument1.Part
        
        If UCase(part1.Name) = UCase("SELECCIONAR_") Then
            MsgBox "Debe seleccionar un P/N para guardar." & vbNewLine & vbNewLine & "Hágalo y vuelva a intentarlo.", vbCritical
            Exit Sub
        End If
        
        Set relationsparte1 = part1.Relations
                    
        Set BodyToRename = partDocument1.Part.Bodies.ITEM(1)

        PNPB = Left(partDocument1.Part.Name, intgr_N_PN)
                    
        Grupo = Mid(part1.Name, intgr_POS_GRUPO, 1)
        
        Ruta = RUTA_SALIDA & Grupo & "00\3D\"
        
        Nombre_Ruta = Ruta & part1.Name
                 
        Nombre_Archivo = Mid(partDocument1.Name, 1, InStr(1, partDocument1.Name, ".") - 1)
            
        Nombre_Ruta_Archivo_Guardado = partDocument1.FullName
        
        Archivo_Existente = CATIA.FileSystem.FileExists(Nombre_Ruta & ".CATPart")
        
        Archivo_Existente_Previo = CATIA.FileSystem.FileExists(Nombre_Ruta_Archivo_Guardado)
            
        Nombre_Cambio = Ruta & part1.Name & "_CAMBIO" & ".CATPart"
                
        Cambiar = Right(Nombre_Ruta_Archivo_Guardado, Len("_CAMBIO.CATPart"))
                
        '4 - SI EL NOMBRE DE LA PARTE NO COINCIDE CON EL NOMBRE DEL ARCHIVO SE SALE DE LA SUBRUTINA Y SE PIDE SINCRONIZAR LA PARTE -SE DECIDIÓ NO PERMITIR GUARDAR PARTES NO SINCRONIZADAS, NO ES INDISPENSABLE-
        '===================================================================================================================================================================================================
        If UCase(Nombre_Archivo) <> UCase(part1.Name) And Archivo_Existente_Previo = True And UCase(Cambiar) <> UCase("_CAMBIO.CATPart") Then
            MsgBox "Se debe sincronizar la parte antes de guardarla (1)" & vbNewLine & "Los siguientes items deben llamarse de la misma manera:" _
            & vbNewLine & vbNewLine & "(1) Columna Excel 'Part Number Catia' = P/N_DESCRIPCION" & vbNewLine & "(2) Archivo en Windows = P/N_DESCRIPCION" _
            & vbNewLine & "(3) 'Part Number' en CATIA = P/N_DESCRIPCION" _
            , vbCritical, "[4] Problema de sincronización! " & part1.Name
            'MsgBox Nombre_Archivo & " -- " & part1.Name
            Exit Sub
        ElseIf UCase(Nombre_Archivo) <> UCase(part1.Name) And Archivo_Existente_Previo = True And UCase(Cambiar) = UCase("_CAMBIO.CATPart") Then
            On Error Resume Next
            Err.Clear
            CATIA.StartCommand ("Clear History")
            partDocument1.SaveAs (Nombre_Ruta)
            
            'SI HAY UN ERROR EN EL GUARDADO EVITA BORRAR EL ARCHIVO ORIGINAL
            '================================================================
            Mata = True
            If CATIA.FileSystem.FileExists(Nombre_Ruta) = False Then
                Mata = False
            End If
            
            If Err.Number <> 0 Then
                Mata = False
            End If
            
            If Mata = True Then
                BodyToRename.Name = PNPB
                Kill (Nombre_Ruta_Archivo_Guardado)
                Exit Sub
            Else
                MsgBox "La parte no ha podido guardarse debido a que usted no ha aceptado las condiciones de la ventana previa." _
                & vbNewLine & vbNewLine & "Vuelva a intentarlo.", vbCritical
                Exit Sub
            End If
            On Error GoTo 0
            
        End If
        
        'SI EL ARCHIVO YA TIENE UNA RUTA (SIGNIFICA QUE SE ESTA TRABAJANDO SOBRE UN ARCHIVO YA EXISTENTE)
        '===============================================================================================
        If UCase(Ruta) = UCase(partDocument1.Path) & "\" And Archivo_Existente = True Then
            BodyToRename.Name = PNPB
            partDocument1.Save
            Exit Sub
       
       'SI EL ARCHIVO NO TIENE UN NOMBRE O TIENE UNA RUTA QUE NO COINCIDE CON LA RUTA CORRECTA (ES NUEVO)
       '================================================================================================
        ElseIf UCase(Ruta) <> UCase(partDocument1.Path) & "\" Then
            'MsgBox Ruta
            'MsgBox partDocument1.Path & "\"
            'SI EXISTE, SIGNIFICA QUE EL ARCHIVO NUEVO LO VA A REEMPLAZAR, SE DA AVISO
            '=========================================================================
            If Archivo_Existente = True Then
            Reemplazo = MsgBox("El archivo ya se encuentra creado, desea reemplazarlo?", vbOKCancel, "Atención!!")
                If Reemplazo = vbOK Then
                    BodyToRename.Name = PNPB
                    CATIA.StartCommand ("Clear History")
                    partDocument1.SaveAs (Nombre_Ruta)
                    Exit Sub
                ElseIf Reemplazo = vbCancel Then
                    MsgBox "El archivo no fue guardado", vbCritical, "Atención!"
                    Exit Sub
                End If
            'SI NO EXISTE AQUI ES DONDE UN ARCHIVO SE GUARDA POR PRIMERA VEZ
            '===============================================================
            Else
                'MsgBox Nombre_Ruta
                BodyToRename.Name = PNPB
                CATIA.StartCommand ("Clear History")
                partDocument1.SaveAs (Nombre_Ruta)
            End If
        
        'SI LA RUTA DEL P/N ES CORRECTA PERO EL ARCHIVO NO EXISTE, SIGNIFICA QUE
        'EL ARCHIVO ESTA CARGADO EN LA SESIÓN PERO SE HA BORRADO DE WINDOWS
        '=======================================================================
        Else
            MsgBox "El archivo aha sido dańado, es probable que se haya perdido.", vbCritical
            CATIA.StartCommand ("Clear History")
            partDocument1.SaveAs (Nombre_Ruta)
        End If
    
    '=====================================================================================================================================================================
    'SI EL ARCHIVO ES UN DRAWING
    '=====================================================================================================================================================================
    ElseIf UCase(Tipo_Archivo) = UCase("DrawingDocument") Then
    
        Dim drawingDocument1 As DrawingDocument
        Set drawingDocument1 = CATIA.ActiveDocument
        
        Dim parameters2 As Parameters
        Set parameters2 = drawingDocument1.Parameters
        
        Dim strParam2 As StrParam
        Set strParam2 = parameters2.ITEM("Drawing\NUMERO DE PLANO")
        
        Dim parameters3 As Parameters
        Set parameters3 = drawingDocument1.Parameters
        
        Dim strParam3 As StrParam
        Set strParam3 = parameters3.ITEM("Drawing\DESIGNACION PRINCIPAL")
        
        Grupo = Mid(strParam2.Value, intgr_POS_GRUPO, 1)
        
        Ruta = RUTA_SALIDA & Grupo & "00\2D\"
                
        Nombre_Ruta = Ruta & strParam2.Value & "_" & strParam3.Value & ".CATDrawing"

        On Error Resume Next
        Err.Clear
        drawingDocument1.SaveAs (Nombre_Ruta)
        On Error GoTo 0
        
        If Err.Number <> 0 Then
            MsgBox "El archivo no ha sido guardado!", vbCritical
            Exit Sub
        End If
        
    End If
    
End If


End Sub

Attribute VB_Name = "A2_Insertar_Parte"
'AUTOR: SEBASTIAN ASSAIN
'NOMBRE: A2_INSERTAR PARTE F50
'VERSION 2.0
'FECHA: 02/04/2020
'CAMBIOS: SE LINKEO CON UNA SUBRUTINA QUE ALMACENA RUTAS
'FRASE: NO PUEDES COMETER 2 VECES EL MISMO ERROR, LA SEGUNDA VEZ SERÁ POR ELECCIÓN
'DESCRIPCIÓN: INSERTA PARTES USANDO DATOS DE UNA TABLA DE DISEŃO INDICADA EN ESTE CÓDIGO.
Public STR_NIV As Variant
Public STR_CSI As String
Public STR_NORD As Variant
Public STR_PN As String
Public STR_DES As String
Public STR_CANT As Variant
Public STR_AUT As String
Public STR_EST As String

Public STR_TEC As String
Public STR_MAT As String
Public STR_TIP As String
Public STR_OBD As String
Public STR_TIP_MAT As String

Public STR_ANCHO As String
Public BOOL_ANCHO As Boolean
Public BOOL_LARGO As Boolean
Public BOOL_ESPES As Boolean
Public BOOL_DIAM As Boolean

Public BOOL_BLOCK_MAT_PRIM As Boolean
Public BOOL_MAT_PRIM As Boolean
Public STR_ESTADO_INI As String
Public STR_GRUPO As String
Public STR_PROD_SEMI As String
Public STR_DES_MAT As String
Public STR_NRO_PARTE_MAT As String
Public STR_ESTADO_TERMIC As String
Public STR_NORM_MAT_PRIM As String
Public STR_APP As String
Public STR_NDP As String

Public STR_DIM As String

Public NO_CREAR As Boolean
Public ARR_COLUMNAS() As Variant
Public ARR_PN() As Variant

Sub CATMain()

CATIA.DisplayFileAlerts = False

Dim oseleccion As Selection
Dim documents1 As Documents
Dim document1 As Document
Dim partDocument1 As PartDocument
Dim selection1 As Selection
Dim visPropertySet1 As VisPropertySet
Dim part1 As Part
Dim product1 As Product
Dim products1 As Products
Dim originElements1 As OriginElements
Dim hybridShapePlaneExplicit1 As HybridShapePlaneExplicit
Dim hybridShapePlaneExplicit2 As HybridShapePlaneExplicit
Dim hybridShapePlaneExplicit3 As HybridShapePlaneExplicit
Dim bSTR1 As String
Dim bSTR2 As String
Dim hybridBodies1 As HybridBodies
Dim hybridBody1 As HybridBody
Dim relations1 As Relations
Dim parameters1 As Parameters
Dim intParam1 As IntParam
Dim strParam1 As StrParam
Dim intParam2 As IntParam
Dim strParam2 As StrParam
Dim strParam3 As StrParam
Dim intParam3 As IntParam
Dim strParam4 As StrParam
Dim strParam5 As StrParam
Dim strParam6 As StrParam
Dim strParam7 As StrParam
Dim strParam8 As StrParam
Dim strParam9 As StrParam
Dim strParam10 As StrParam
Dim strParam11 As StrParam
Dim strParam12 As StrParam
Dim strParam13 As StrParam
Dim strParam14 As StrParam
Dim strParam15 As StrParam
Dim strParam16 As StrParam
Dim dimension1 As Dimension
Dim dimension2 As Dimension
Dim dimension3 As Dimension
Dim length1 As Length
Dim length2 As Length
Dim length3 As Length
Dim length4 As Length
Dim intParam4 As IntParam
Dim intParam5 As IntParam
Dim intParam7 As IntParam
Dim Param As Parameter
Dim parameters2 As Parameters
Dim parameter1 As Parameter
Dim parameters3 As Parameters
Dim parameter2 As Parameter
Dim RUTA_SALIDA As String

Call SetearUnidades

If CATIA.Documents.Count <> 0 Or CATIA.Windows.Count <> 0 Then
    Call PROYECTO(PROY_CODE, PROYS, ARM_SYS)
End If

Call Rutas("ESTRUCTURA", RUTA_SALIDA, PROY_CODE)

BOOL_MAT_PRIM = False

If CATIA.Documents.Count = 0 Or CATIA.Windows.Count = 0 Then
    GoTo 1

Else
    Set oseleccion = CATIA.ActiveDocument.Selection

    If TypeName(CATIA.ActiveDocument) = "ProductDocument" Then

        If oseleccion.Count = 1 Then

            'SI SE SELECCIONA UN PARÁMETRO LA SUBRUTINA NO HARÁ NADA
            '=======================================================
            If InStr(1, UCase(TypeName(oseleccion.ITEM(1).Value)), UCase("Param")) > 0 Then
                Exit Sub
            End If

            If TypeName(oseleccion.ITEM(1).Value.ReferenceProduct.Parent) = "PartDocument" Then

                On Error GoTo MensajeError

                Set product1 = oseleccion.ITEM(1).LeafProduct.Parent.Parent.Parent

                Set products1 = product1.Products
                
                Set parameters1 = product1.Parameters

                'SE CHEQUEA QUE EL ESTÁNDAR ESTÉ DENTRO DE UN COMPONENT Y NO UN PRODUCT
                '======================================================================
                Set objProd = oseleccion.ITEM(1).LeafProduct.Parent.Parent
                If Not ProductIsComponent(objProd) Then
                    MsgBox "El estándar debe estar dentro del Component (no Product) correspondiente.", vbCritical, "Corregir ubicación de estándar."
                    Exit Sub
                End If
                
                'NO SE ADMITE COLOCAR CANTIDAD DE PARTES DE UN PN DEL PROYECTO
                '=============================================================
                If InStr(1, oseleccion.ITEM(1).Value.ReferenceProduct.Parent.Product.Name, PROY_CODE) > 0 Then
                    Exit Sub
                End If
                
                'SE CREA EL PARÁMETRO Y SE BORRA PARA FORZAR UN ERROR EN CASO DE QUE EL ESTÁNDAR NO SE ENCUENTRE EN LA POSICIÓN CORRECTA
                '=======================================================================================================================
                If Not ParameterExist(parameters1, oseleccion.ITEM(1).Value.ReferenceProduct.Parent.Product.Name, Param) Then
                    Set strparameter80 = parameters1.CreateInteger(oseleccion.ITEM(1).Value.ReferenceProduct.Parent.Product.Name, 1)
                    parameters1.Remove (product1.Name & "\" & oseleccion.ITEM(1).Value.ReferenceProduct.Parent.Product.Name)
                End If
                
                'SE PIDE AL USUARIO QUE INTRODUZCA LA CANTIDAD DE ESTÁNDARES
                '===========================================================
                n_do = n_do + 1
                CANTIDAD_LISTO = True
                Cantidad_Parte = InputBox("Introduzca la cantidad del PN:" & vbNewLine & oseleccion.ITEM(1).Value.ReferenceProduct.Parent.Product.Name & vbNewLine _
                & vbNewLine & "[Si introduce -1 el sistema lo leerá como una cantidad indefinida o a demanda del taller.]", "Cantidad..", "-1")

                'SI SE PRESIONA 'CANCEL' TERMINA LA SUB-RUTINA
                '=============================================
                If StrPtr(Cantidad_Parte) = 0 Then
                    Exit Sub
                End If

                If IsNumeric(Cantidad_Parte) = False Then
                    MsgBox "Debe ser un valor numérico.", vbCritical, "Error.."
                    Exit Sub
                End If
                
                'CATIA_MACROS_PROYECTOS
                          
                If Not ParameterExist(parameters1, oseleccion.ITEM(1).Value.ReferenceProduct.Parent.Product.Name, Param) Then
                    Set strparameter80 = parameters1.CreateInteger(oseleccion.ITEM(1).Value.ReferenceProduct.Parent.Product.Name, Int(Cantidad_Parte))
                Else
                    Set strparameter80 = parameters1.ITEM(product1.Name & "\" & oseleccion.ITEM(1).Value.ReferenceProduct.Parent.Product.Name)
                    strparameter80.Value = Int(Cantidad_Parte)
                End If
                
                Exit Sub
                
MensajeError:   MsgBox "El estándar debe estar dentro del Component correspondiente.", vbCritical, "Corregir ubicación de estándar."
                
            ElseIf TypeName(oseleccion.ITEM(1).Value.ReferenceProduct.Parent) = "ProductDocument" Then
                
                Set product1 = oseleccion.ITEM(1).Value.ReferenceProduct.Parent.Product
                Set products1 = product1.Products
                Set parameters1 = product1.Parameters
                
2               NO_CREAR = True
                BOOL_BLOCK_MAT_PRIM = False
                
                UserForm9.Show
                
                If NO_CREAR = True Then
                    Exit Sub
                End If
                
                UserForm91.Show
                
                If NO_CREAR = True Then
                    Exit Sub
                End If
                
                If UCase(STR_DIM) = "LENGTH" Then
                    STR_NOMBRE_DIM = "Largo"
                ElseIf UCase(STR_DIM) = "AREA" Then
                    STR_NOMBRE_DIM = "Area"
                ElseIf UCase(STR_DIM) = "VOLUME" Then
                    STR_NOMBRE_DIM = "Volumen"
                ElseIf UCase(STR_DIM) = "MASS" Then
                    STR_NOMBRE_DIM = "Masa"
                End If
                
                'SI SE INSERTA UNA MATERIA PRIMA, LA MISMA SE INSERTA COMO PARÁMETRO EN EL ÁRBOL DEL PRODUCTO
                '============================================================================================
                If BOOL_MAT_PRIM = True Then
                    
                    'SI YA SE ENCUENTRA CREADO NO SE CREA
                    If Not ParameterExist(parameters1, STR_PN & "|" & STR_NOMBRE_DIM, Param) Then
                        Set dimension3 = parameters1.CreateDimension(STR_PN & "|" & STR_NOMBRE_DIM, STR_DIM, 0#)
                    End If
                    
                    Exit Sub
                    
                End If
                
                Dim product3 As Product
                Set product3 = products1.AddNewComponent("Part", "")
                
                'Nombre del archivo parte creada =====> MsgBox product3.ReferenceProduct.Parent.Name

                Set documents1 = CATIA.Documents

                Dim move1 As Move
                Set move1 = product3.Move

                Set move1 = move1.MovableObject

                Dim arrayOfVariantOfDouble1(11)
                arrayOfVariantOfDouble1(0) = 1#
                arrayOfVariantOfDouble1(1) = 0#
                arrayOfVariantOfDouble1(2) = 0#
                arrayOfVariantOfDouble1(3) = 0#
                arrayOfVariantOfDouble1(4) = 1#
                arrayOfVariantOfDouble1(5) = 0#
                arrayOfVariantOfDouble1(6) = 0#
                arrayOfVariantOfDouble1(7) = 0#
                arrayOfVariantOfDouble1(8) = 1#
                arrayOfVariantOfDouble1(9) = 0#
                arrayOfVariantOfDouble1(10) = 0#
                arrayOfVariantOfDouble1(11) = 0#
                Set move1Variant = move1
                move1Variant.Apply arrayOfVariantOfDouble1

                Set partDocument1 = documents1.ITEM(product3.ReferenceProduct.Parent.Name)
                Set part1 = partDocument1.Part
                Set relations1 = part1.Relations
                Set parameters1 = part1.Parameters

                Set strParam14 = parameters1.CreateString("CSI", STR_CSI)
                Set strParam2 = parameters1.CreateString("Autor", STR_AUT)

                Set strParam3 = parameters1.CreateString("Tipo de Pieza", STR_TIP)
                Set strParam4 = parameters1.CreateString("Tec y Sub Tec", STR_TEC)
                Set strParam5 = parameters1.CreateString("Material Obtenido de", STR_OBD)
                Set strParam9 = parameters1.CreateString("Tipo de Material", STR_TIP_MAT)

                If STR_TEC <> "20-1" Then
                
                    Set strParam13 = parameters1.CreateString("Designacion de Materia Prima", STR_DES_MAT)
                    Set strParam12 = parameters1.CreateString("Norma de Materia Prima", STR_NORM_MAT_PRIM)
                    Set strParam15 = parameters1.CreateString("Estado Inicial de Material", STR_ESTADO_INI)
                    Set strParam16 = parameters1.CreateString("Estado Final de Material", STR_ESTADO_TERMIC)

                    If BOOL_ANCHO = True Then
                        Set length1 = parameters1.CreateDimension("Ancho", "LENGTH", 0#)
                    End If
    
                    If BOOL_LARGO = True Then
                        Set length2 = parameters1.CreateDimension("Largo", "LENGTH", 0#)
                    End If
    
                    If BOOL_ESPES = True Then
                        Set length3 = parameters1.CreateDimension(STR_ANCHO, "LENGTH", 0#)
                    End If
    
                    If BOOL_DIAM = True Then
                        Set length4 = parameters1.CreateDimension("Diametro", "LENGTH", 0#)
                    End If
                
                    Call GeoSetsCompuestos
                
                End If

                Set dimension1 = parameters1.CreateDimension("Masa", "MASS", 0#)

                Set parameters2 = part1.Parameters
                Set parameter1 = parameters2.ITEM("Part Number")
                parameter1.ValuateFromString (STR_PN & "_" & STR_DES)
                Set parameters3 = part1.Parameters
                Set parameter2 = parameters3.ITEM("Product Description")
                parameter2.ValuateFromString (STR_DES)

                part1.Update

                Set selection1 = oseleccion
                Set visPropertySet1 = selection1.VisProperties
                Set originElements1 = part1.OriginElements
                Set hybridShapePlaneExplicit1 = originElements1.PlaneXY

                selection1.Clear

                selection1.Add hybridShapePlaneExplicit1

                Set hybridShapePlaneExplicit2 = originElements1.PlaneYZ

                selection1.Add hybridShapePlaneExplicit2

                Set hybridShapePlaneExplicit3 = originElements1.PlaneZX

                selection1.Add hybridShapePlaneExplicit3

                Set visPropertySet1 = visPropertySet1.Parent

                bSTR1 = visPropertySet1.Name
                bSTR2 = visPropertySet1.Name

                visPropertySet1.SetShow 1

                selection1.Clear

                Set hybridBodies1 = part1.HybridBodies

                Set hybridBody2 = hybridBodies1.Add()
                hybridBody2.Name = "Rivets"

                Set hybridBody3 = hybridBodies1.Add()
                hybridBody3.Name = "FT&A"

                Set hybridBody1 = hybridBodies1.Add()
                hybridBody1.Name = "Geometría Auxiliar"

                part1.Update

                'SE SELECCIONA LA PARTE PARA ENTRAR A LA SUBRUTINA DE GUARDADO"
                '===========================================================================================
                Set sel = CATIA.ActiveDocument.Selection
                A_SELECCIONAR = "'Assembly Design'.Part.Part Number='" & STR_PN & "_" & STR_DES & "',all"
                Call sel.Search(A_SELECCIONAR)
                '===========================================================================================

                Call A1_Guardar.CATMain

            End If

        ElseIf oseleccion.Count > 1 Then

            MsgBox "Usted debe seleccionar solo un producto donde insertar la parte!", vbCritical, "Seleccione sólo uno.."
            Exit Sub

        ElseIf oseleccion.Count = 0 Then
    
1           NO_CREAR = True
            BOOL_BLOCK_MAT_PRIM = True
            
            UserForm9.Show

            If NO_CREAR = True Then
                Exit Sub
            End If
            
            UserForm91.Show
            
            If NO_CREAR = True Then
                Exit Sub
            End If
    
            BOOL_MAT_PRIM = False
    
            Set documents1 = CATIA.Documents
            Set partDocument1 = documents1.Add("Part")
            Set selection1 = partDocument1.Selection
            Set visPropertySet1 = selection1.VisProperties
            Set part1 = partDocument1.Part
            Set originElements1 = part1.OriginElements
            Set hybridShapePlaneExplicit1 = originElements1.PlaneXY
            
            selection1.Add hybridShapePlaneExplicit1
            
            Set hybridShapePlaneExplicit2 = originElements1.PlaneYZ
            
            selection1.Add hybridShapePlaneExplicit2
            
            Set hybridShapePlaneExplicit3 = originElements1.PlaneZX
            
            selection1.Add hybridShapePlaneExplicit3
            
            Set visPropertySet1 = visPropertySet1.Parent
            
            bSTR1 = visPropertySet1.Name
            bSTR2 = visPropertySet1.Name
            visPropertySet1.SetShow 1
            
            selection1.Clear
            
            Set hybridBodies1 = part1.HybridBodies
    
            Set hybridBody2 = hybridBodies1.Add()
            hybridBody2.Name = "Rivets"
            
            Set hybridBody3 = hybridBodies1.Add()
            hybridBody3.Name = "FT&A"
            
            Set hybridBody1 = hybridBodies1.Add()
            hybridBody1.Name = "Geometría Auxiliar"
            
            part1.Update
    
            Set relations1 = part1.Relations
            Set parameters1 = part1.Parameters
            
            Set strParam14 = parameters1.CreateString("CSI", STR_CSI)
            Set strParam2 = parameters1.CreateString("Autor", STR_AUT)
            
            Set strParam3 = parameters1.CreateString("Tipo de Pieza", STR_TIP)
            Set strParam4 = parameters1.CreateString("Tec y Sub Tec", STR_TEC)
            Set strParam5 = parameters1.CreateString("Material Obtenido de", STR_OBD)
            Set strParam9 = parameters1.CreateString("Tipo de Material", STR_TIP_MAT)

            If STR_TEC <> "20-1" Then
                
                Set strParam13 = parameters1.CreateString("Designacion de Materia Prima", STR_DES_MAT)
                Set strParam12 = parameters1.CreateString("Norma de Materia Prima", STR_NORM_MAT_PRIM)
                Set strParam15 = parameters1.CreateString("Estado Inicial de Material", STR_ESTADO_INI)
                Set strParam16 = parameters1.CreateString("Estado Final de Material", STR_ESTADO_TERMIC)

                If BOOL_ANCHO = True Then
                    Set length1 = parameters1.CreateDimension("Ancho", "LENGTH", 0#)
                End If
                
                If BOOL_LARGO = True Then
                    Set length2 = parameters1.CreateDimension("Largo", "LENGTH", 0#)
                End If
                
                If BOOL_ESPES = True Then
                    Set length3 = parameters1.CreateDimension(STR_ANCHO, "LENGTH", 0#)
                End If
                
                If BOOL_DIAM = True Then
                    Set length4 = parameters1.CreateDimension("Diametro", "LENGTH", 0#)
                End If
            
                Call GeoSetsCompuestos
            
            End If

            Set dimension1 = parameters1.CreateDimension("Masa", "MASS", 0#)

            Set parameters2 = part1.Parameters
            Set parameter1 = parameters2.ITEM("Part Number")
            parameter1.ValuateFromString (STR_PN & "_" & STR_DES)
            Set parameters3 = part1.Parameters
            Set parameter2 = parameters3.ITEM("Product Description")
            parameter2.ValuateFromString (STR_DES)
            
            part1.Update
            
            Call A1_Guardar.CATMain
        
        End If
    
    ElseIf TypeName(CATIA.ActiveDocument) = "PartDocument" Then
    
        If oseleccion.Count = 1 Then
    
            Set visProperties1 = CATIA.ActiveDocument.Selection.VisProperties
                   
            NO_CREAR = True
            BOOL_BLOCK_MAT_PRIM = False
            
            UserForm9.Show
            UserForm91.Show
            
            If NO_CREAR = True Then
                Exit Sub
            End If
            
            Set partDocument1 = CATIA.ActiveDocument
            Set part1 = partDocument1.Part
        
            Dim bodies1 As Bodies
            Set bodies1 = part1.Bodies
        
            Dim body1 As Body
'            Set body1 = bodies1.Add()
'
'            body1.Name = STR_PN
            
            Set relations1 = part1.Relations
            Set parameters1 = part1.Parameters
            
            If BOOL_MAT_PRIM = False Then
            
                'SI YA SE ENCUENTRA CREADO NO SE CREA
                If Not ParameterExist(parameters1, STR_PN & "|Designacion", Param) Then
                    Set strParam1 = parameters1.CreateString(STR_PN & "|Designacion", STR_DES)
                End If
                
                'SI YA SE ENCUENTRA CREADO NO SE CREA
                If Not ParameterExist(parameters1, STR_PN & "|Codigo Mat Ref", Param) Then
                    Set strParam1 = parameters1.CreateString(STR_PN & "|Codigo Mat Ref", "")
                End If
                'SI YA SE ENCUENTRA CREADO NO SE CREA
                If Not ParameterExist(parameters1, STR_PN & "|Norma de Materia Prima", Param) Then
                    Set strParam2 = parameters1.CreateString(STR_PN & "|Norma de Materia Prima", STR_NORM_MAT_PRIM)
                End If
                
                'SI YA SE ENCUENTRA CREADO NO SE CREA
                If Not ParameterExist(parameters1, STR_PN & "|Tipo de Pieza", Param) Then
                    Set strParam3 = parameters1.CreateString(STR_PN & "|Tipo de Pieza", STR_TIP)
                End If
                
                'SI YA SE ENCUENTRA CREADO NO SE CREA
                If Not ParameterExist(parameters1, STR_PN & "|Tec y Sub Tec", Param) Then
                    Set strParam4 = parameters1.CreateString(STR_PN & "|Tec y Sub Tec", STR_TEC)
                End If
                
                'SI YA SE ENCUENTRA CREADO NO SE CREA
                If Not ParameterExist(parameters1, STR_PN & "|Material Obtenido de", Param) Then
                    Set strParam5 = parameters1.CreateString(STR_PN & "|Material Obtenido de", STR_OBD)
                End If
                
                'SI YA SE ENCUENTRA CREADO NO SE CREA
                If Not ParameterExist(parameters1, STR_PN & "|Tipo de Material", Param) Then
                    Set strParam9 = parameters1.CreateString(STR_PN & "|Tipo de Material", STR_TIP_MAT)
                End If
                
                'SI YA SE ENCUENTRA CREADO NO SE CREA
                If Not ParameterExist(parameters1, STR_PN & "|Masa", Param) Then
                    Set dimension1 = parameters1.CreateDimension(STR_PN & "|Masa", "MASS", 0#)
                End If

                If BOOL_ANCHO = True Then
                    'SI YA SE ENCUENTRA CREADO NO SE CREA
                    If Not ParameterExist(parameters1, STR_PN & "|Ancho", Param) Then
                        Set length1 = parameters1.CreateDimension(STR_PN & "|Ancho", "LENGTH", 0#)
                    End If
                End If
                
                If BOOL_LARGO = True Then
                    'SI YA SE ENCUENTRA CREADO NO SE CREA
                    If Not ParameterExist(parameters1, STR_PN & "|Largo", Param) Then
                        Set length2 = parameters1.CreateDimension(STR_PN & "|Largo", "LENGTH", 0#)
                    End If
                End If
                
                If BOOL_ESPES = True Then
                    'SI YA SE ENCUENTRA CREADO NO SE CREA
                    If Not ParameterExist(parameters1, STR_PN & "|Espesor", Param) Then
                        Set length3 = parameters1.CreateDimension(STR_PN & "|" & STR_ANCHO, "LENGTH", 0#)
                    End If
                End If
                
                If BOOL_DIAM = True Then
                    'SI YA SE ENCUENTRA CREADO NO SE CREA
                    If Not ParameterExist(parameters1, STR_PN & "|Diametro", Param) Then
                        Set length4 = parameters1.CreateDimension(STR_PN & "|Diametro", "LENGTH", 0#)
                    End If
                End If
            Else

                If UCase(STR_DIM) = "LENGTH" Then
                    STR_NOMBRE_DIM = "Largo"
                ElseIf UCase(STR_DIM) = "AREA" Then
                    STR_NOMBRE_DIM = "Area"
                ElseIf UCase(STR_DIM) = "VOLUME" Then
                    STR_NOMBRE_DIM = "Volumen"
                ElseIf UCase(STR_DIM) = "MASS" Then
                    STR_NOMBRE_DIM = "Masa"
                End If
                
                'SI YA SE ENCUENTRA CREADO NO SE CREA
                If Not ParameterExist(parameters1, STR_PN & "|" & STR_NOMBRE_DIM, Param) Then
                    Set dimension3 = parameters1.CreateDimension(STR_PN & "|" & STR_NOMBRE_DIM, STR_DIM, 0#)
                End If
                
            End If
            
            part1.Update
        
        Else
        
            GoTo 1
        
        End If
        
    Else
    
        MsgBox "Esta acción escapa a los previsto. Comuniquesé con el desarrollador del código.", vbCritical, "Límite coder.."
        Exit Sub
        
    End If

End If

End Sub

Public Function ParameterExist(ByRef ParameterCollection As Parameters, ByVal ParameterName As String, ByRef OutputParameter As Parameter) As Boolean
    On Error Resume Next
    Err.Clear
    Set OutputParameter = ParameterCollection.ITEM(ParameterName)
    If Err.Number = 0 Then
        ParameterExist = True
    Else
        ParameterExist = False
    End If
    On Error GoTo 0
End Function

Function ProductIsComponent(iProduct) As Boolean

'oseleccion.ITEM(1).LeafProduct.Parent.Parent

Set objDoc = iProduct.ReferenceProduct.Parent
Set objParentDoc = iProduct.Parent.Parent.ReferenceProduct.Parent
ProductIsComponent = (objDoc Is objParentDoc)

End Function

Attribute VB_Name = "A3_Insertar_Producto"
'AUTOR: SEBASTIAN ASSAIN
'NOMBRE: A3_INSERTAR PRODUCTO F50
'VERSION 1.2
'FECHA: 02/04/2020
'CAMBIOS: SE LINKEO A UNA SUBRUTINA QUE AGRUPA TODAS LAS RUTAS NECESARIAS
'FRASE: NO PUEDES COMETER 2 VECES EL MISMO ERROR, LA SEGUNDA VEZ SERÁ POR ELECCIÓN
'DESCRIPCIÓN: INSERTA PRODUCTOS USANDO DATOS DE UNA TABLA DE DISEŃO INDICADA EN ESTE CÓDIGO.
Sub CATMain()
CATIA.DisplayFileAlerts = False

Dim oseleccion As Selection
Dim documents1 As Documents
Dim document1 As Document
'La variable "partDocument" es un producto en este caso
Dim partDocument1 As ProductDocument
Dim selection1 As Selection
Dim visPropertySet1 As VisPropertySet
'la variable "part1" es un producto en este caso
Dim part1 As Product
Dim originElements1 As OriginElements
Dim hybridShapePlaneExplicit1 As HybridShapePlaneExplicit
Dim hybridShapePlaneExplicit2 As HybridShapePlaneExplicit
Dim hybridShapePlaneExplicit3 As HybridShapePlaneExplicit
Dim bSTR1 As String
Dim bSTR2 As String
Dim hybridBodies1 As HybridBodies
Dim hybridBody1 As HybridBody
Dim relations1 As Relations
Dim parameters1 As Parameters
Dim intParam1 As IntParam
Dim strParam1 As StrParam
Dim intParam2 As IntParam
Dim strParam2 As StrParam
Dim strParam3 As StrParam
Dim intParam3 As IntParam
Dim strParam4 As StrParam
Dim strParam5 As StrParam
Dim strParam6 As StrParam
Dim strParam7 As StrParam
Dim strParam8 As StrParam
Dim strParam9 As StrParam
Dim strParam10 As StrParam
Dim strParam11 As StrParam
Dim strParam14 As StrParam
Dim dimension1 As Dimension
Dim length1 As Length
Dim length2 As Length
Dim length3 As Length
Dim intParam4 As IntParam
Dim intParam5 As IntParam
Dim StringParam12 As StrParam
Dim dimension2 As StrParam
Dim intParam7 As IntParam
Dim parameters2 As Parameters
Dim parameter1 As Parameter
Dim parameters3 As Parameters
Dim parameter2 As Parameter
Dim RUTA_SALIDA As String
Dim sel As Selection
Dim A_SELECCIONAR As String

Call SetearUnidades

If CATIA.Documents.Count <> 0 Or CATIA.Windows.Count <> 0 Then
    Call PROYECTO(PROY_CODE, PROYS, ARM_SYS)
End If

Call Rutas("ESTRUCTURA", RUTA_SALIDA, PROY_CODE)

If CATIA.Documents.Count = 0 Or CATIA.Windows.Count = 0 Then
    GoTo 1

ElseIf CATIA.Documents.Count > 0 Or CATIA.Windows.Count > 0 Then
    Set oseleccion = CATIA.ActiveDocument.Selection
        
    If oseleccion.Count = 1 Then
        
        If TypeName(oseleccion.ITEM(1).Value.ReferenceProduct.Parent) = "PartDocument" Then
            MsgBox "Usted esta intentando insertar un producto dentro de una parte, suerte!", vbCritical
            Exit Sub
        
        ElseIf TypeName(oseleccion.ITEM(1).Value.ReferenceProduct.Parent) = "ProductDocument" Then
            
            BOOL_MAT_PRIM = False
            BOOL_BLOCK_MAT_PRIM = True
            
            NO_CREAR = True
            
            UserForm9.Show
            
            If NO_CREAR = True Then
                Exit Sub
            End If
             
            Dim product1 As Product
            Set product1 = oseleccion.ITEM(1).Value.ReferenceProduct.Parent.Product
            
            Dim products1 As Products
            Set products1 = product1.Products
            
            Dim product3 As Product
            Set product3 = products1.AddNewComponent("Product", "")
            
            Set documents1 = CATIA.Documents
            
            Dim move1 As Move
            Set move1 = product3.Move
            
            Set move1 = move1.MovableObject
            
            Dim arrayOfVariantOfDouble1(11)
            arrayOfVariantOfDouble1(0) = 1#
            arrayOfVariantOfDouble1(1) = 0#
            arrayOfVariantOfDouble1(2) = 0#
            arrayOfVariantOfDouble1(3) = 0#
            arrayOfVariantOfDouble1(4) = 1#
            arrayOfVariantOfDouble1(5) = 0#
            arrayOfVariantOfDouble1(6) = 0#
            arrayOfVariantOfDouble1(7) = 0#
            arrayOfVariantOfDouble1(8) = 1#
            arrayOfVariantOfDouble1(9) = 0#
            arrayOfVariantOfDouble1(10) = 0#
            arrayOfVariantOfDouble1(11) = 0#
            
            Set partDocument1 = documents1.ITEM(product3.ReferenceProduct.Parent.Name)
            Set part1 = partDocument1.Product
            Set relations1 = part1.Relations
            Set parameters1 = part1.Parameters
            
            Set strParam14 = parameters1.CreateString("CSI", STR_CSI)
            Set strParam2 = parameters1.CreateString("Autor", STR_AUT)
            Set dimension1 = parameters1.CreateDimension("Masa", "MASS", 0#)
            Set strParam9 = parameters1.CreateString("Código_ATA", "")

            CATIA.StartCommand ("Clear History")
            
            Set parameters2 = part1.Parameters
            Set parameter1 = parameters2.ITEM("Part Number")
            parameter1.ValuateFromString (STR_PN & "_" & STR_DES)
            Set parameters3 = part1.Parameters
            Set parameter2 = parameters3.ITEM("Product Description")
            parameter2.ValuateFromString (STR_DES)
            
            part1.Update

            'SE SELECCIONA EL PRODUCTO PARA ENTRAR A LA SUBRUTINA DE GUARDADO"
            '===========================================================================================
            Set sel = CATIA.ActiveDocument.Selection
            A_SELECCIONAR = "'Assembly Design'.Product.Part Number='" & STR_PN & "_" & STR_DES & "',all"
            Call sel.Search(A_SELECCIONAR)
            '===========================================================================================

            Call A1_Guardar.CATMain
        
        End If
    
    ElseIf oseleccion.Count > 1 Then
        MsgBox "Usted debe seleccionar solo un producto donde insertar el producto!", vbCritical
        Exit Sub
    
    ElseIf oseleccion.Count = 0 Then
1       NO_CREAR = True
            
        UserForm9.Show
            
        If NO_CREAR = True Then
            Exit Sub
        End If

        Set documents1 = CATIA.Documents
        Set partDocument1 = documents1.Add("Product")
        Set selection1 = partDocument1.Selection
        Set visPropertySet1 = selection1.VisProperties
        Set part1 = partDocument1.Product
        
        Set visPropertySet1 = visPropertySet1.Parent
        
        bSTR1 = visPropertySet1.Name
        
        bSTR2 = visPropertySet1.Name
        
        visPropertySet1.SetShow 1
        
        selection1.Clear
                
        part1.Update
        
        Set relations1 = part1.Relations
        Set parameters1 = part1.Parameters
        
        Set strParam14 = parameters1.CreateString("CSI", STR_CSI)
        Set strParam4 = parameters1.CreateString("Autor", STR_AUT)
        Set dimension1 = parameters1.CreateDimension("Masa", "MASS", 0#)
        Set strParam6 = parameters1.CreateString("Código_ATA", "")

        CATIA.StartCommand ("Clear History")
        Set parameters2 = part1.Parameters
        Set parameter1 = parameters2.ITEM("Part Number")
        parameter1.ValuateFromString (STR_PN & "_" & STR_DES)
        Set parameters3 = part1.Parameters
        Set parameter2 = parameters3.ITEM("Product Description")
        parameter2.ValuateFromString (STR_DES)

        part1.Update
        
        Set sel = CATIA.ActiveDocument.Selection
        
        A_SELECCIONAR = "'Assembly Design'.Product.Part Number='" & STR_PN & "_" & STR_DES & "',all"
        Call sel.Search(A_SELECCIONAR)
        
        Call A1_Guardar.CATMain
    
    End If
End If

End Sub

Attribute VB_Name = "A4_Insertar_Plano"
'AUTOR: SEBASTIAN ASSAIN
'NOMBRE: A4_INSERTAR PLANO
'VERSION 1.0
'FECHA: 02/04/2020
'CAMBIOS: SE LINKEO A UNA SUBRUTINA QUE AGRUPA TODAS LAS RUTAS NECESARIAS
Public PN As String
Public DESC As String
Public CSI As String

Sub CATMain()

Dim Ruta_Plantilla As String
Dim UserForm1 As New UserForm1

If CATIA.Documents.Count = 0 Or CATIA.Windows.Count = 0 Then
    MsgBox "Debe tener abierto al menos un documento para utilizar esta herramienta", vbCritical
    Exit Sub
End If

Call PROYECTO(PROY_CODE, PROYS, ARM_SYS)

'NUMEROS ENTEROS PARA TRABAJAR CON PART NUMBERS
'==============================================
Call Param_PN(ARR_PN, PROY_CODE)

intgr_POS_GRUPO = ARR_PN(2)
intgr_TIPO_PN = ARR_PN(3)

str_PROD_MAX = ARR_PN(6)
str_PROD_MIN = ARR_PN(7)
'==============================================

'NUMEROS ENTEROS PARA TRABAJAR CON PART NUMBERS
'=========================================================================================================================================================================================================================================
intgr_N_PN = ARR_PN(1)
intgr_INI_DESC = intgr_N_PN + 2 'LA DESCRIPCIÓN COMIENZA EN LA POSICIÓN 17:  F  5  -  C  -  2  1  3  4  2  5  -  4  0  1  .  P  R  O  D  U  C  T  O  1
'                                                                                                                            |
'                                                                                                                           (17)
intgr_LONG_TIPO = ARR_PN(4)
intgr_INI_DWG_PN = ARR_PN(5) + 1 'EN CASO DE FOKKER SE PEUDEN CREAR ARCHIVOS AUXILIARES PARA HACER PLANOS, AL HACERLO EL PN COMIENZA MAS ADELANTE: D  W  G  1  -  F  5  -  C  -  2  1  3  4  2  5  -  4  0  1
'                                                                                                                                                                 |
'                                                                                                                                                                (6)
'
intgr_INI_DWG_DESC = intgr_INI_DESC + intgr_INI_DWG_PN - 1 'TENIENDO EN CUANTA LA ADICIÓN DE 'DWG1', LA DESCRIPCIÓN COMIENZA EN LA POSICIÓN 22:  D  W  G  1  -  F  5  -  C  -  2  1  3  4  2  5  -  4  0  1  .  P  R  O  D  U  C  T  O  1
'                                                                                                                                                                                                               |
'                                                                                                                                                                                                              (22)
'=========================================================================================================================================================================================================================================

If TypeName(CATIA.ActiveDocument) = "ProductDocument" Then
    
    Dim productDocument1 As ProductDocument
            
    Set productDocument1 = CATIA.ActiveDocument
    
    DESC_CATPRODUCT = Mid(CATIA.ActiveDocument.Name, intgr_INI_DESC)
    
    DESC = Mid(DESC_CATPRODUCT, 1, InStr(1, DESC_CATPRODUCT, ".CATProduct") - 1)
    
    PN = Left(CATIA.ActiveDocument.Name, intgr_N_PN)
    
    On Error GoTo MensajeError
    CSI = CATIA.ActiveDocument.Product.Parameters.RootParameterSet.DirectParameters.ITEM("CSI").ValueAsString
    On Error GoTo 0
    
    If Left(PN, 3) = "DWG" Then
        PN = Mid(CATIA.ActiveDocument.Name, intgr_INI_DWG_PN, intgr_N_PN)
        DESC_CATPRODUCT = Mid(CATIA.ActiveDocument.Name, intgr_INI_DWG_DESC)
        DESC = Mid(DESC_CATPRODUCT, 1, InStr(1, DESC_CATPRODUCT, ".CATProduct") - 1)
    End If
    
ElseIf TypeName(CATIA.ActiveDocument) = "PartDocument" Then
    
    Dim partDocument1 As PartDocument
            
    Set partDocument1 = CATIA.ActiveDocument
    
    DESC_CATPRODUCT = Mid(CATIA.ActiveDocument.Name, intgr_INI_DESC)
    
    DESC = Mid(DESC_CATPRODUCT, 1, InStr(1, DESC_CATPRODUCT, ".CATPart") - 1)
    
    PN = Left(CATIA.ActiveDocument.Name, intgr_N_PN)
    
    On Error GoTo MensajeError
    CSI = CATIA.ActiveDocument.Part.Parameters.RootParameterSet.DirectParameters.ITEM("CSI").ValueAsString
    On Error GoTo 0

    If PN = "SELECCIONAR_" Then
        MsgBox "Primero debe guardar la parte con la Macro", vbCritical
        Exit Sub
    End If

ElseIf TypeName(CATIA.ActiveDocument) = "DrawingDocument" Then
    
    MsgBox "Usted esta intentando hacer un plano de un plano. Siéntese y medítelo.", vbCritical
    Exit Sub
       
End If
    
UserForm1.Show vbModeless

Exit Sub

MensajeError: MsgBox "Debe completar el parámetro CSI para continuar.", vbCritical, "Requisitos mínimos para 2D."

End Sub

Attribute VB_Name = "A55_Generar_Capturas"
'http://www.scripting4v5.com/additional-articles/catia-macro-captures-annotations/
Option Compare Text

Sub CATMain()
 
If CATIA.Documents.Count = 0 Or CATIA.Windows.Count = 0 Then
    MsgBox "Debe tener abierto al menos un documento para utilizar esta herramienta", vbCritical
    Exit Sub
End If
 
If TypeName(CATIA.ActiveDocument) <> "PartDocument" Then
    MsgBox "Sólo se pueden hacer capturas trabajando dentro de un CATPart", vbCritical + vbOKOnly, "Por acá no.."
    Exit Sub
End If

UserForm3.Show vbModeless

End Sub

Sub FTA_generator(PARTE, VISTAS())

Dim fta As HybridBody
Dim id As HybridBody
Dim gyb As HybridBody
Dim vista As Camera3D
Dim captura As Capture
Dim vp As TPSView
Dim plano As Plane
Dim ann As AnnotationSet
Dim nombre As String


Set doc = CATIA.ActiveDocument

If TypeName(CATIA.ActiveDocument) = "ProductDocument" Then
    MsgBox "Sólo se pueden hacer capturas trabajando dentro de un CATPart", vbCritical + vbOKOnly, "Por acá no.."
    Exit Sub
    Set PARTE = CATIA.ActiveDocument.Product
ElseIf TypeName(CATIA.ActiveDocument) = "PartDocument" Then
    Set PARTE = CATIA.ActiveDocument.Part
End If

On Error Resume Next
'genera geometrical sets...
EXISTE = True
If Len(PARTE.HybridBodies.ITEM("FT&A").Name) = 0 Then 'esta declaracion no tiene sentido si no existe el parametro, es solo para que salte el error
    If Err.Number <> 0 Then
    EXISTE = False
    End If
End If
On Error GoTo 0

If EXISTE = False Then
    Set fta = PARTE.HybridBodies.Add
    fta.Name = "FT&A"
    Set fta = PARTE.HybridBodies.ITEM("FT&A")
Else
    Set fta = PARTE.HybridBodies.ITEM("FT&A")
End If

On Error Resume Next
'genera geometrical sets...
EXISTE = True
If Len(fta.HybridBodies.ITEM("ID").Name) = 0 Then 'esta declaracion no tiene sentido si no existe el parametro, es solo para que salte el error
    If Err.Number <> 0 Then
    EXISTE = False
    End If
End If
On Error GoTo 0

If EXISTE = False Then
    Set id = fta.HybridBodies.Add
    id.Name = "ID"
End If

On Error Resume Next
'genera geometrical sets...
EXISTE = True
If Len(fta.HybridBodies.ITEM("BONDING").Name) = 0 Then 'esta declaracion no tiene sentido si no existe el parametro, es solo para que salte el error
    If Err.Number <> 0 Then
    EXISTE = False
    End If
End If
On Error GoTo 0

If EXISTE = False Then
    Set gyb = fta.HybridBodies.Add
    gyb.Name = "BONDING"
End If


On Error Resume Next
'genera geometrical sets...
EXISTE = True
If Len(fta.HybridBodies.ITEM("VIEWS").Name) = 0 Then 'esta declaracion no tiene sentido si no existe el parametro, es solo para que salte el error
    If Err.Number <> 0 Then
    EXISTE = False
    End If
End If
On Error GoTo 0

If EXISTE = False Then
    Set view_1 = fta.HybridBodies.Add
    view_1.Name = "VIEWS"
End If


On Error Resume Next
'genera geometrical sets...
EXISTE = True
If Len(fta.HybridBodies.ITEM("HOLES").Name) = 0 Then 'esta declaracion no tiene sentido si no existe el parametro, es solo para que salte el error
    If Err.Number <> 0 Then
    EXISTE = False
    End If
End If
On Error GoTo 0

If EXISTE = False Then
    Set Hole = fta.HybridBodies.Add
    Hole.Name = "HOLES"
End If

'genera anotaciones y viewpoint...
Set plano = PARTE.OriginElements.PlaneXY
Set ann = PARTE.AnnotationSets.Add("dummy")
Set vp = ann.TPSViewFactory.CreateView(plano, 1)

If CATIA.ActiveDocument.Part.AnnotationSets.ITEM(1).Captures.Count > 0 Then
    opc_yn = MsgBox("Ya hay capturas generadas. Desea agregar nuevas?", vbYesNo)
    If opc_yn = vbYes Then
    
    Else
        Exit Sub
    End If
End If

'genera vistas y capturas...
For i = 1 To UBound(VISTAS)
    nombre = VISTAS(i)
    n_capturas = CATIA.ActiveDocument.Part.AnnotationSets.ITEM(1).Captures.Count

        Set vista = CATIA.ActiveWindow.activeviewer.NewCamera()
        vista.Name = nombre
        Set captura = ann.CaptureFactory.CreateCapture
        captura.Name = nombre
        captura.ActiveViewState = True
        captura.ActiveView = vp
        captura.ViewPoint = True
        captura.Camera = vista

Next
    
PARTE.Update
End Sub

Attribute VB_Name = "A5_Publicar_Body"
'AUTOR: SEBASTIAN ASSAIN
'NOMBRE: A5_PUBLICAR_BODY
'VERSION 1.0
'FECHA: 02/04/2020
'CAMBIOS: -
'FRASE: NO PUEDES COMETER 2 VECES EL MISMO ERROR, LA SEGUNDA VEZ SERÁ POR ELECCIÓN
'DESCRIPCIÓN: PUBLICA EL BODY DE LA PARTE
Public PUB As String
Sub CATMain()

Dim PUB2 As String
Dim BODYNAME As String

Call PROYECTO(PROY_CODE, PROYS, ARM_SYS)

'NUMEROS ENTEROS PARA TRABAJAR CON PART NUMBERS
'==============================================
Call Param_PN(ARR_PN, PROY_CODE)
intgr_N_PN = ARR_PN(1)
'==============================================
                                                                
'SI NO EXISTE NINGUN DOCUMENTO ABIERTO SE EVITA QUE LA MACRO DEVUELVA UN ERROR
'=============================================================================
If CATIA.Documents.Count = 0 Or CATIA.Windows.Count = 0 Then
    MsgBox "Debe tener abierto al menos un documento para utilizar esta herramienta", vbCritical
    Exit Sub
End If

If TypeName(CATIA.ActiveDocument) = "PartDocument" Then

    Dim partDocument1 As PartDocument
    
    If CATIA.Documents.Count = 0 Or CATIA.Windows.Count = 0 Then
        MsgBox "Debe tener abierto al menos un documento para utilizar esta herramienta", vbCritical
        Exit Sub
    End If

    Set partDocument1 = CATIA.ActiveDocument
    
    Nombre_Archivo = Mid(partDocument1.Name, 1, InStr(1, partDocument1.Name, ".CATPart") - 1)
                    
    If Left(Nombre_Archivo, 3) = "DD3" Then
        MsgBox "No se recomienda publicar el Body de una parte LIBERADA. No podrá guardarla.", vbInformation
    End If
    
    partDocumentName = Left(partDocument1.Name, intgr_N_PN)
    
    PUB = partDocument1.Part.Name
    BODYNAME = partDocument1.Part.Bodies.ITEM(1).Name
    
        If BODYNAME = "PartBody" Then
            MsgBox "Por favor asigne un nombre al PartBody!" & vbNewLine & vbNewLine & "Si guarda la parte usando la Macro se asignará el nombre correspondiente al PartBody", vbInformation
            Exit Sub
        ElseIf BODYNAME <> partDocumentName Then
            MsgBox "Por favor asigne el nombre correcto al PartBody!" & vbNewLine & vbNewLine & "Si guarda la parte usando la Macro se asignará el nombre correspondiente al PartBody", vbInformation
            Exit Sub
        End If
    
    PUB2 = PUB & "/!" & BODYNAME
    
    Dim product1 As Product
    Set product1 = partDocument1.GetItem(PUB)
    
    
    Dim reference1 As Reference
    Set reference1 = product1.CreateReferenceFromName(PUB2)
    
    Dim publications1 As Publications
    Set publications1 = product1.Publications
    

    On Error Resume Next
        
        If publications1.ITEM(1).Name = BODYNAME Then
            If Err.Number = 0 Then
                ExistePub = MsgBox("El PartBody que está intentando publicar ya existe." & vbNewLine & vbNewLine & "Desea reemplazarlo?", vbYesNo + vbCritical)
                If ExistePub = vbYes Then
                    publications1.Remove (BODYNAME)
                ElseIf ExistePub = vbNo Then
                    Exit Sub
                End If
            End If
        ElseIf Left(publications1.ITEM(1).Name, 5) = Left(BODYNAME, 5) Then
           ExistePubA = MsgBox("Al parecer ya existe una pblicación anterior." & vbNewLine & vbNewLine & "Desea reemplazarla?", vbYesNo + vbCritical)
           If ExistePubA = vbYes Then
                NomPub = publications1.ITEM(1).Name
                publications1.Remove (NomPub)
            ElseIf ExistePubA = vbNo Then
                Exit Sub
            End If
        End If
    
    Dim publication1 As Publication
    Set publication1 = publications1.Add(BODYNAME)
    
    publications1.SetDirect BODYNAME, reference1
    
    Dim settingControllers1 As SettingControllers
    Set settingControllers1 = CATIA.SettingControllers
    
    Dim visualizationSettingAtt1 As VisualizationSettingAtt
    Set visualizationSettingAtt1 = settingControllers1.ITEM("CATVizVisualizationSettingCtrl")
    
    visualizationSettingAtt1.SaveRepository

Else

    MsgBox "Sólo se pueden hacer publicaciones trabajando dentro de un CATPart", vbCritical + vbOKOnly, "Por acá tampoco.."

End If
    

End Sub

Attribute VB_Name = "A6_Sincronizar"
'AUTOR: SEBASTIAN ASSAIN
'NOMBRE: A6_Sincronizar
'VERSION 1.0
'FECHA: 02/04/2020
'CAMBIOS:
'FRASE:
'DESCRIPCIÓN: AGREGA LOS RESPONSABLES Y PARÁMETROS ASIGNADOS EN LA TABLA DE EXCEL A MODELOS DE PARTES Y PLANOS.
Public no_resp As Boolean
Public N_CSI As String
Public PN_FOR_CSI As String

Sub CATMain()
Dim parameters1 As Parameters
Dim strParam1 As StrParam
Dim intParam1 As IntParam
Dim realParam As realParam
Dim FECHA_VALOR As String
Dim REV_APROBADOR_VALOR As String
Dim IMI_VALOR As String

Call SetearUnidades

'SI NO EXISTE NINGUN DOCUMENTO ABIERTO SE EVITA QUE LA MACRO DEVUELVA UN ERROR
'=============================================================================
If CATIA.Documents.Count = 0 Or CATIA.Windows.Count = 0 Then
    MsgBox "Debe tener abierto al menos un documento para utilizar esta herramienta", vbCritical
    Exit Sub
End If

Call PROYECTO(PROY_CODE, PROYS, ARM_SYS)

'NUMEROS ENTEROS PARA TRABAJAR CON PART NUMBERS
'==============================================
Call Param_PN(ARR_PN, PROY_CODE)
intgr_N_PN = ARR_PN(1)
intgr_POS_GRUPO = ARR_PN(2)
'==============================================

'=======================================================================================================================================================
'SI EL ARCHIVO ES UNA PARTE
'=======================================================================================================================================================
If TypeName(CATIA.ActiveDocument) = "PartDocument" Then

    Dim partDocument1 As PartDocument
    Set partDocument1 = CATIA.ActiveDocument
    
    Dim part1 As Part
    Set part1 = partDocument1.Part
    
    Dim selection1 As Selection
    Set selection1 = partDocument1.Selection
    
    Set selection2 = CATIA.ActiveDocument.Selection
    
    Set parameters1 = part1.Parameters
    Dim Param As Parameter
    
    'SI NO HAY NADA SELECCIONADO, SE EVITA ESTA BLOQUE
    If selection2.Count <> 0 Then
        
        'SI EL USUARIO SELECCIONA DEL ARBOL DE PARÁMETROS UN SET DE PARÁMETROS, ESTOS SE PUEDEN ACTUALIZAR
        If InStr(1, selection2.ITEM(1).Value.Name, "Tipo de Pieza") <> 0 Or InStr(1, selection2.ITEM(1).Value.Name, "Tec y Sub Tec") <> 0 _
        Or InStr(1, selection2.ITEM(1).Value.Name, "Material Obtenido de") <> 0 Or InStr(1, selection2.ITEM(1).Value.Name, "Tipo de Material") <> 0 _
        Or InStr(1, selection2.ITEM(1).Value.Name, "Norma de Materia Prima") <> 0 Then
        
            'SE DISCRIMINA SI LOS PARAMETROS PERTENECEN A LA PARTE O A LOS NUCLEOS QUE LA CONFORMAN
            If InStr(1, selection2.ITEM(1).Value.Name, "|") <> 0 Then '<----SI EL PARÁMETRO TIENE EL SÍMBOLO '|' SIGNIFICA QUE ES UN NUCLEO O UN INSERTO DENTRO DE LA PARTE.
            
                Aux_Split_1 = Split(selection2.ITEM(1).Value.Name, "|")
                Aux_Split_2 = Split(Aux_Split_1(0), "\")
                
                If InStr(1, selection2.ITEM(1).Value.Name, "Norma de Materia Prima") <> 0 Then
                    
                    BOOL_MAT_PRIM = True
                    
                    UserForm9.Show
                    Unload UserForm91
                    
                    If NO_CREAR = True Then
                        Exit Sub
                    End If
                    
                    'SI EL PARAMETRO EXISTE SE LO ACTUALIZA, SINO SE LO CREA PRIMERO Y SE LO ACTUALIZA DESPUES.
                    If ParameterExist(parameters1, Aux_Split_1(0) & "|Norma de Materia Prima", Param) Then
                        Set stringParam1 = parameters1.ITEM(Aux_Split_1(0) & "|Norma de Materia Prima")
                        stringParam1.Value = STR_NORM_MAT_PRIM
                    Else
                        Set stringParam1 = parameters1.CreateString(Aux_Split_2(1) & "|Norma de Materia Prima", STR_NORM_MAT_PRIM)
                    End If
                    
                    BOOL_MAT_PRIM = False
                
                Else
                    BOOL_MAT_PRIM = False
                    
                    UserForm91.Show
                    
                    If NO_CREAR = True Then
                        Exit Sub
                    End If
                    
                    'SI EL PARAMETRO EXISTE SE LO ACTUALIZA, SINO SE LO CREA PRIMERO Y SE LO ACTUALIZA DESPUES.
                    If ParameterExist(parameters1, Aux_Split_1(0) & "|Tipo de Pieza", Param) Then
                        Set stringParam1 = parameters1.ITEM(Aux_Split_1(0) & "|Tipo de Pieza")
                        stringParam1.Value = STR_TIP
                    Else
                       Set stringParam1 = parameters1.CreateString(Aux_Split_2(1) & "|Tipo de Pieza", STR_TIP)
                    End If
                    'SI EL PARAMETRO EXISTE SE LO ACTUALIZA, SINO SE LO CREA PRIMERO Y SE LO ACTUALIZA DESPUES.
                    If ParameterExist(parameters1, Aux_Split_1(0) & "|Tec y Sub Tec", Param) Then
                        Set stringParam1 = parameters1.ITEM(Aux_Split_1(0) & "|Tec y Sub Tec")
                        stringParam1.Value = STR_TEC
                    Else
                        Set stringParam1 = parameters1.CreateString(Aux_Split_2(1) & "|Tec y Sub Tec", STR_TEC)
                    End If
                    'SI EL PARAMETRO EXISTE SE LO ACTUALIZA, SINO SE LO CREA PRIMERO Y SE LO ACTUALIZA DESPUES.
                    If ParameterExist(parameters1, Aux_Split_1(0) & "|Material Obtenido de", Param) Then
                        Set stringParam1 = parameters1.ITEM(Aux_Split_1(0) & "|Material Obtenido de")
                        stringParam1.Value = STR_OBD
                    Else
                        Set stringParam1 = parameters1.CreateString(Aux_Split_2(1) & "|Material Obtenido de", STR_OBD)
                    End If
                    'SI EL PARAMETRO EXISTE SE LO ACTUALIZA, SINO SE LO CREA PRIMERO Y SE LO ACTUALIZA DESPUES.
                    If ParameterExist(parameters1, Aux_Split_1(0) & "|Tipo de Material", Param) Then
                        Set stringParam1 = parameters1.ITEM(Aux_Split_1(0) & "|Tipo de Material")
                        stringParam1.Value = STR_TIP_MAT
                    Else
                        Set stringParam1 = parameters1.CreateString(Aux_Split_2(1) & "|Tipo de Material", STR_TIP_MAT)
                    End If
                End If
                
                Exit Sub
                
            Else '<----SI EL PARÁMETRO NO TIENE EL SÍMBOLO '|' SIGNIFICA QUE SON LO PARÁMETROS DE LA PARTE.
                
                BOOL_MAT_PRIM = False
                
                UserForm91.Show
                
                If NO_CREAR = True Then
                    Exit Sub
                End If
                
                'SI EL PARAMETRO EXISTE SE LO ACTUALIZA, SINO SE LO CREA PRIMERO Y SE LO ACTUALIZA DESPUES.
                If ParameterExist(parameters1, "Tipo de Pieza", Param) Then
                    Set stringParam1 = parameters1.ITEM("Tipo de Pieza")
                    stringParam1.Value = STR_TIP
                Else
                   Set stringParam1 = parameters1.CreateString("Tipo de Pieza", STR_TIP)
                End If
                'SI EL PARAMETRO EXISTE SE LO ACTUALIZA, SINO SE LO CREA PRIMERO Y SE LO ACTUALIZA DESPUES.
                If ParameterExist(parameters1, "Tec y Sub Tec", Param) Then
                    Set stringParam1 = parameters1.ITEM("Tec y Sub Tec")
                    stringParam1.Value = STR_TEC
                Else
                    Set stringParam1 = parameters1.CreateString("Tec y Sub Tec", STR_TEC)
                End If
                'SI EL PARAMETRO EXISTE SE LO ACTUALIZA, SINO SE LO CREA PRIMERO Y SE LO ACTUALIZA DESPUES.
                If ParameterExist(parameters1, "Material Obtenido de", Param) Then
                    Set stringParam1 = parameters1.ITEM("Material Obtenido de")
                    stringParam1.Value = STR_OBD
                Else
                    Set stringParam1 = parameters1.CreateString("Material Obtenido de", STR_OBD)
                End If
                'SI EL PARAMETRO EXISTE SE LO ACTUALIZA, SINO SE LO CREA PRIMERO Y SE LO ACTUALIZA DESPUES.
                If ParameterExist(parameters1, "Tipo de Material", Param) Then
                    Set stringParam1 = parameters1.ITEM("Tipo de Material")
                    stringParam1.Value = STR_TIP_MAT
                Else
                    Set stringParam1 = parameters1.CreateString("Tipo de Material", STR_TIP_MAT)
                End If
                
                Exit Sub

            End If
            
        ElseIf InStr(1, selection2.ITEM(1).Value.Name, "Designacion de Materia Prima") <> 0 Or InStr(1, selection2.ITEM(1).Value.Name, "Norma de Materia Prima") <> 0 _
        Or InStr(1, selection2.ITEM(1).Value.Name, "Estado Inicial de Material") <> 0 Or InStr(1, selection2.ITEM(1).Value.Name, "Estado Final de Material") <> 0 Then
            
            BOOL_MAT_PRIM = True
            
            UserForm9.Show
            Unload UserForm91
            
            If NO_CREAR = True Then
                Exit Sub
            End If
            
            'SI EL PARAMETRO EXISTE SE LO ACTUALIZA, SINO SE LO CREA PRIMERO Y SE LO ACTUALIZA DESPUES.
            If ParameterExist(parameters1, "Designacion de Materia Prima", Param) Then
                Set stringParam1 = parameters1.ITEM("Designacion de Materia Prima")
                stringParam1.Value = STR_DES_MAT
            Else
                Set stringParam1 = parameters1.CreateString("Designacion de Materia Prima", STR_DES_MAT)
            End If
            'SI EL PARAMETRO EXISTE SE LO ACTUALIZA, SINO SE LO CREA PRIMERO Y SE LO ACTUALIZA DESPUES.
            If ParameterExist(parameters1, "Norma de Materia Prima", Param) Then
                Set stringParam1 = parameters1.ITEM("Norma de Materia Prima")
                stringParam1.Value = STR_NORM_MAT_PRIM
            Else
               Set stringParam1 = parameters1.CreateString("Norma de Materia Prima", STR_NORM_MAT_PRIM)
            End If
            'SI EL PARAMETRO EXISTE SE LO ACTUALIZA, SINO SE LO CREA PRIMERO Y SE LO ACTUALIZA DESPUES.
            If ParameterExist(parameters1, "Estado Inicial de Material", Param) Then
                Set stringParam1 = parameters1.ITEM("Estado Inicial de Material")
                stringParam1.Value = STR_ESTADO_INI
            Else
                Set stringParam1 = parameters1.CreateString("Estado Inicial de Material", STR_ESTADO_INI)
            End If
            'SI EL PARAMETRO EXISTE SE LO ACTUALIZA, SINO SE LO CREA PRIMERO Y SE LO ACTUALIZA DESPUES.
            If ParameterExist(parameters1, "Estado Final de Material", Param) Then
                Set stringParam1 = parameters1.ITEM("Estado Final de Material")
                stringParam1.Value = STR_ESTADO_TERMIC
            Else
                Set stringParam1 = parameters1.CreateString("Estado Final de Material", STR_ESTADO_TERMIC)
            End If
            
            BOOL_MAT_PRIM = False
            
            Exit Sub
        
        End If
    
    End If
    
    Nombre_Archivo = Mid(partDocument1.Name, 1, InStr(1, partDocument1.Name, ".CATPart") - 1)

    If Left(Nombre_Archivo, 3) = "DD3" Then
        MsgBox "No es posible SINCRONIZAR una parte LIBERADA.", vbCritical
        Exit Sub
    End If

    PNAUX = Split(part1.Name, "_")
    PN = PNAUX(0)
    
    msgerror = False
    
    TIPO_DOC = "DD3"
    Call BuscarRev(PN, REV, msgerror, TIPO_DOC, "PARTE")
    
    If msgerror = True Then
        Exit Sub
    End If
    
    REV_count = Asc(REV) - 64
    
    'SE ANALIZA SI LA PARTE YA TIENE LOS RESPONSABLES ASIGNADOS
    '==========================================================
    YA_TA = False

    For i = 1 To REV_count
        FECHA_VALOR = "FECHA_" & Chr(64 + i)
        Fecha = False
        If ParameterExist(parameters1, FECHA_VALOR, Param) Then
            Fecha = True
        End If
    Next

    For i = 1 To REV_count
        REV_APROBADOR_VALOR = "REV_" & Chr(64 + i)
        REV_APROBADOR = False
        If ParameterExist(parameters1, REV_APROBADOR_VALOR, Param) Then
            REV_APROBADOR = True
        End If
    Next
    
    'SE VERIFICA SI ESTAN TODOS LOS
    For i = 1 To REV_count
        IMI_VALOR = "IMI_" & Chr(64 + i)
        IMI = False
        If ParameterExist(parameters1, IMI_VALOR, Param) Then
            IMI = True
        End If
    Next
         
    no_resp = False
            
    Call VerResponsables(PN, REV_count, N_FAB, N_REV, N_SIS, N_RES, N_APR, ESTADO_FAB, ESTADO_REV, ESTADO_SIS, ESTADO_RES, ESTADO_APR, N_Nivel, N_Cantidad, N_Numero_Parte, N_Nro_Ord, N_Autor, N_Estado, N_Tipo, N_MATERIAL, no_resp)

    'SE ASIGNA EL CSI, SI LA PARTE SE ENCUENTRA EN MUCHOS CONJUNTOS SE PIDE ASIGNAR EL CSI
    '=====================================================================================
    PN_FOR_CSI = PN
    UserForm7.Show
    
    'SI FALTA DE ASIGNAR EL CONJUNTO INMEDIAT SUPERIOR, SE CREA EL PARAMETRO CORRESPONDIENTE
    '=======================================================================================
    On Error Resume Next
    Err.Clear
    If ParameterExist(parameters1, "CSI", Param) Then
        Set strParam1 = parameters1.ITEM(part1.Name & "\CSI")
        strParam1.Value = N_CSI
    Else
        Set strParam1 = parameters1.CreateString("CSI", "")
        Dim arrayOfVariantOfBSTR21(0)
        arrayOfVariantOfBSTR21(0) = N_CSI
        Set strParam1Variant = strParam1
        strParam1Variant.SetEnumerateValues arrayOfVariantOfBSTR21
        strParam1.Value = N_CSI
    End If
    
    If ParameterExist(parameters1, "Autor", Param) Then
        Set strParam1 = parameters1.ITEM(part1.Name & "\Autor")
        strParam1.Value = N_Autor
    Else
        Set strParam1 = parameters1.CreateString("Autor", "")
        Dim arrayOfVariantOfBSTR13(0)
        arrayOfVariantOfBSTR13(0) = N_Autor
        Set strParam1Variant = strParam1
        strParam1Variant.SetEnumerateValues arrayOfVariantOfBSTR13
        strParam1.Value = N_Autor
    End If
    
    BOOL_PANEL = False '<---- PARA EVITAR ABRIR EL PANEL UserForm91 SE CREA ESTA VARIABLE
    
    If ParameterExist(parameters1, "Tipo de Pieza", Param) Then
        Set stringParam1 = parameters1.ITEM(part1.Name & "\Tipo de Pieza")
        If stringParam1.Value = "" Then
            UserForm91.Show
        
            BOOL_MAT_PRIM = False
            If NO_CREAR = True Then
                Exit Sub
            End If
            stringParam1.Value = STR_TIP
            BOOL_PANEL = True
        End If
    Else
        UserForm91.Show
        If NO_CREAR = True Then
            Exit Sub
        End If
        Set stringParam1 = parameters1.CreateString("Tipo de Pieza", STR_TIP)
        BOOL_PANEL = True
    End If
    
    If ParameterExist(parameters1, "Tec y Sub Tec", Param) Then
        Set stringParam1 = parameters1.ITEM(part1.Name & "\Tec y Sub Tec")
        If stringParam1.Value = "" And BOOL_PANEL = False Then
            UserForm91.Show
            If NO_CREAR = True Then
                Exit Sub
            End If
            stringParam1.Value = STR_TEC
            BOOL_PANEL = True
        ElseIf stringParam1.Value = "" And BOOL_PANEL = True Then
            stringParam1.Value = STR_TEC
        End If
    Else
        If BOOL_PANEL = False Then
            UserForm91.Show
            If NO_CREAR = True Then
                Exit Sub
            End If
            BOOL_PANEL = True
        End If
        Set stringParam1 = parameters1.CreateString("Tec y Sub Tec", STR_TEC)
    End If
    
    If ParameterExist(parameters1, "Material Obtenido de", Param) Then
        Set stringParam1 = parameters1.ITEM(part1.Name & "\Material Obtenido de")
        If stringParam1.Value = "" And BOOL_PANEL = False Then
            UserForm91.Show
            If NO_CREAR = True Then
                Exit Sub
            End If
            stringParam1.Value = STR_OBD
            BOOL_PANEL = True
        ElseIf stringParam1.Value = "" And BOOL_PANEL = True Then
            stringParam1.Value = STR_OBD
        End If
    Else
        If BOOL_PANEL = False Then
            UserForm91.Show
            If NO_CREAR = True Then
                Exit Sub
            End If
            BOOL_PANEL = True
        End If
        Set stringParam1 = parameters1.CreateString("Material Obtenido de", STR_OBD)
    End If
    
    If ParameterExist(parameters1, "Tipo de Material", Param) Then
        Set stringParam1 = parameters1.ITEM(part1.Name & "\Tipo de Material")
        If stringParam1.Value = "" And BOOL_PANEL = False Then
            UserForm91.Show
            If NO_CREAR = True Then
                Exit Sub
            End If
            stringParam1.Value = STR_TIP_MAT
            BOOL_PANEL = True
        ElseIf stringParam1.Value = "" And BOOL_PANEL = True Then
            stringParam1.Value = STR_TIP_MAT
        End If
    Else
        If BOOL_PANEL = False Then
            UserForm91.Show
            If NO_CREAR = True Then
                Exit Sub
            End If
            BOOL_PANEL = True
        End If
        Set stringParam1 = parameters1.CreateString("Tipo de Material", STR_TIP_MAT)
    End If
        
    On Error GoTo 0
    
    If ParameterExist(parameters1, "Tec y Sub Tec", Param) = True Then
        STR_TEC = Param.ValueAsString
    End If
        
    If STR_TEC <> "20-1" Then
        
        If ParameterExist(parameters1, "Designacion de Materia Prima", Param) Then
            Set stringParam1 = parameters1.ITEM(part1.Name & "\Designacion de Materia Prima")
            If stringParam1.Value = "" And BOOL_PANEL = False Then
                UserForm91.Show
                If NO_CREAR = True Then
                    Exit Sub
                End If
                stringParam1.Value = STR_DES_MAT
                BOOL_PANEL = True
            ElseIf stringParam1.Value = "" And BOOL_PANEL = True Then
                stringParam1.Value = STR_DES_MAT
            End If
        Else
            If BOOL_PANEL = False Then
                UserForm91.Show
                If NO_CREAR = True Then
                    Exit Sub
                End If
                BOOL_PANEL = True
            End If
            Set stringParam1 = parameters1.CreateString("Designacion de Materia Prima", STR_DES_MAT)
        End If
        
        If ParameterExist(parameters1, "Norma de Materia Prima", Param) Then
            Set stringParam1 = parameters1.ITEM(part1.Name & "\Norma de Materia Prima")
            If stringParam1.Value = "" And BOOL_PANEL = False Then
                UserForm91.Show
                If NO_CREAR = True Then
                    Exit Sub
                End If
                stringParam1.Value = STR_NORM_MAT_PRIM
                BOOL_PANEL = True
            ElseIf stringParam1.Value = "" And BOOL_PANEL = True Then
                stringParam1.Value = STR_NORM_MAT_PRIM
            End If
        Else
            If BOOL_PANEL = False Then
                UserForm91.Show
                If NO_CREAR = True Then
                    Exit Sub
                End If
                BOOL_PANEL = True
            End If
            Set stringParam1 = parameters1.CreateString("Norma de Materia Prima", STR_NORM_MAT_PRIM)
        End If
        
        If ParameterExist(parameters1, "Estado Inicial de Material", Param) Then
        'EL ESTADO INICIAL DE LA MATERIA PRIMA MUCHAS VECES SE DEJA VACÍO, SE EVITA ABRIR EL PANEL SÓLO PARA ESTE DATO.
            Set stringParam1 = parameters1.ITEM(part1.Name & "\Estado Inicial de Material")
            If stringParam1.Value = "" Then
                stringParam1.Value = STR_ESTADO_INI
            End If
        Else
            If BOOL_PANEL = False Then
                UserForm91.Show
                If NO_CREAR = True Then
                    Exit Sub
                End If
                BOOL_PANEL = True
            End If
            Set stringParam1 = parameters1.CreateString("Estado Inicial de Material", STR_ESTADO_INI)
        End If
        
        If ParameterExist(parameters1, "Estado Final de Material", Param) Then
            Set stringParam1 = parameters1.ITEM(part1.Name & "\Estado Final de Material")
            If stringParam1.Value = "" And BOOL_PANEL = False Then
                UserForm91.Show
                If NO_CREAR = True Then
                    Exit Sub
                End If
                stringParam1.Value = STR_ESTADO_TERMIC
                BOOL_PANEL = True
            ElseIf stringParam1.Value = "" And BOOL_PANEL = True Then
                stringParam1.Value = STR_ESTADO_TERMIC
            End If
        Else
            If BOOL_PANEL = False Then
                UserForm91.Show
                If NO_CREAR = True Then
                    Exit Sub
                End If
                BOOL_PANEL = True
            End If
            Set stringParam1 = parameters1.CreateString("Estado Final de Material", STR_ESTADO_TERMIC)
        End If
        
        DiamOK = True
        AnchoOK = False
        LargoOK = False
        EspesorOK = False
        
        'SI EXISTE DIÁMETRO Y OTRA DIMENSION (LARGO O ESPESOR) DECLARA QUE NO ES NECESARIO AGREGAR MAS PARÁMETROS
        '========================================================================================================
        If ParameterExist(parameters1, "Diametro", Param) Then
            'SI EXISTE DIÁMETRO SÓLO SE NECESITA QUE EXISTA UNA DIMENSIÓN MÁS PARA DEFINIR LA PARTE
            If ParameterExist(parameters1, "Largo", Param) Or ParameterExist(parameters1, "Espesor", Param) Or ParameterExist(parameters1, "Alto", Param) Then
                AnchoOK = True
                LargoOK = True
                EspesorOK = True
            ElseIf ParameterExist(parameters1, "Largo", Param) And ParameterExist(parameters1, "Espesor", Param) And ParameterExist(parameters1, "Alto", Param) Then
                LargoOK = False
            End If
        Else
            If ParameterExist(parameters1, "Ancho", Param) Then
                AnchoOK = True
            End If
            If ParameterExist(parameters1, "Largo", Param) Then
                LargoOK = True
            End If
            If ParameterExist(parameters1, "Espesor", Param) Or ParameterExist(parameters1, "Alto", Param) Then
                EspesorOK = True
            End If
        End If
    
        If DiamOK = False Then
        Set length1 = parameters1.CreateDimension("Diametro", "LENGTH", 0#)
        End If
    
        If AnchoOK = False Then
        Set length1 = parameters1.CreateDimension("Ancho", "LENGTH", 0#)
        End If
    
        If LargoOK = False Then
            Set length2 = parameters1.CreateDimension("Largo", "LENGTH", 0#)
        End If
    
        If EspesorOK = False Then
            Set length3 = parameters1.CreateDimension("Espesor", "LENGTH", 0#)
        End If
    
    ElseIf STR_TEC = "20-1" Then
    
        Call GeoSetsCompuestos
    
    End If 'STR_TEC <> "20-1"

    If Not ParameterExist(parameters1, "Masa", Param) Then
        Set dimension1 = parameters1.CreateDimension("Masa", "MASS", 0#)
    End If
    
    'SI SE GENERA UN NUEVO MATERIAL POR ERROR, SE LO BORRA.
    On Error Resume Next
    If ParameterExist(parameters1, "Material.1", Param) Then
        Set strParam1 = parameters1.ITEM(part1.Name & "\Material.1")
        parameters1.Remove (part1.Name & "\Material.1")
    End If
    On Error GoTo 0

    If Err.Number <> 0 Then
        MsgBox "Hay un error en la carga del Conjunto Inmediato Superior (CSI). Corrija la tabla para poder continuar.", vbCritical, "Error en CSI."
    End If
    
    If no_resp = True Then
        Exit Sub
    End If
    
    'SE DEBE IGRESAR EL IMI (INDICE DE MODIFICACIÓN) PARA CONTINUAR, SIEMPRE SE LO PIDE POR SI SE QUIERE MODIFICARLO
    '===============================================================================================================
    Do While IMI_CHECK <> True
        IMI_CHECK = True
        imi_rev = InputBox("Introduzca el IMI correspondiente a la revisión: " & REV, "Indice de Modificación", "00")

        'SI SE PRESIONA 'CANCEL' SE SALE
        If StrPtr(imi_rev) = 0 Then
            Exit Sub
        End If

        'SE VERIFICA QUE EL IMI SE ENCUENTRE BIEN ESCRITO
        If Len(imi_rev) <> 2 Then
            MsgBox "El numero IMI debe estar compuesto de dos caracteres. Vuelva a intentarlo e introduzcalo correctamente.", vbCritical, "Error de formato."
            IMI_CHECK = False
        End If
        
        'SE VERIFICA QUE EL IMI NO SEA IGUAL AL DE LA REVISIÓN ANTERIOR
        If REV <> "A" Then
            For i = 1 To REV_count - 1
                IMI_VALOR_ANTERIOR = "IMI_" & Chr(Asc(REV) - i)
                If imi_rev = parameters1.ITEM(part1.Name & "\" & IMI_VALOR_ANTERIOR).ValueAsString Then
                    MsgBox "Este IMI ya existe en una revisión anterior, debe ser distinto.", vbCritical
                    IMI_CHECK = False
                    Exit For
                End If
            Next
        End If

    Loop

    'SE AGREGA EL IMI CORRESPONDIENTE
    '================================
        If IMI = True Then
            Set strParam1 = parameters1.ITEM(part1.Name & "\" & IMI_VALOR)
            strParam1.Value = imi_rev
        ElseIf IMI = False Then
            Set strParam1 = parameters1.CreateString(IMI_VALOR, "")
            Dim arrayOfVariantOfBSTR8(0)
            arrayOfVariantOfBSTR8(0) = imi_rev
            Set strParam1Variant = strParam1
            strParam1Variant.SetEnumerateValues arrayOfVariantOfBSTR8
            strParam1.Value = imi_rev
        End If
        
    'SI FALTA DE ASIGNAR ALGUN ÁREA REPONSABLE, SE CREA EL PARAMETRO CORRESPONDIENTE, SE AGREGA LA FECHA (NECESARIA PARA LA DOCUMENATACION)
    '======================================================================================================================================
        If Fecha = True Then
'            Set strParam1 = parameters1.ITEM(part1.Name & "\" & FECHA_VALOR)
'            strParam1.Value = Day(Now) & "/" & Month(Now) & "/" & Year(Now)
        ElseIf Fecha = False Then
            Set strParam1 = parameters1.CreateString(FECHA_VALOR, "")
            Dim arrayOfVariantOfBSTR6(0)
            arrayOfVariantOfBSTR6(0) = Day(Now) & "/" & Month(Now) & "/" & Year(Now)
            Set strParam1Variant = strParam1
            strParam1Variant.SetEnumerateValues arrayOfVariantOfBSTR6
            strParam1.Value = Day(Now) & "/" & Month(Now) & "/" & Year(Now)
        End If
    
    If REV_count > 1 Then 'si la parte está en revisión A, el autor será el responsable revisor.
        If REV_APROBADOR = True Then
            Set strParam1 = parameters1.ITEM(part1.Name & "\" & REV_APROBADOR_VALOR)
            strParam1.Value = UCase(Environ("username"))
        ElseIf REV_APROBADOR = False Then
            Set strParam1 = parameters1.CreateString(REV_APROBADOR_VALOR, "")
            Dim arrayOfVariantOfBSTR7(0)
            arrayOfVariantOfBSTR7(0) = UCase(Environ("username"))
            Set strParam1Variant = strParam1
            strParam1Variant.SetEnumerateValues arrayOfVariantOfBSTR7
            strParam1.Value = UCase(Environ("username"))
        End If
    End If
    
    If ParameterExist(parameters1, "ING. FABRIC.", Param) Then
        Set strParam1 = parameters1.ITEM(part1.Name & "\ING. FABRIC.")
        strParam1.Value = N_FAB & "_" & ESTADO_FAB
    Else
        Set strParam1 = parameters1.CreateString("ING. FABRIC.", "")
        Dim arrayOfVariantOfBSTR1(0)
        arrayOfVariantOfBSTR1(0) = N_FAB & "_" & ESTADO_FAB
        Set strParam1Variant = strParam1
        strParam1Variant.SetEnumerateValues arrayOfVariantOfBSTR1
        strParam1.Value = N_FAB & "_" & ESTADO_FAB
    End If
    
    If ParameterExist(parameters1, "REVISÓ", Param) Then
        Set strParam1 = parameters1.ITEM(part1.Name & "\REVISÓ")
        strParam1.Value = N_REV & "_" & ESTADO_REV
    Else
        Set strParam1 = parameters1.CreateString("REVISÓ", "")
        Dim arrayOfVariantOfBSTR2(0)
        arrayOfVariantOfBSTR2(0) = N_REV & "_" & ESTADO_REV
        Set strParam1Variant = strParam1
        strParam1Variant.SetEnumerateValues arrayOfVariantOfBSTR2
        strParam1.Value = N_REV & "_" & ESTADO_REV
    End If
    
    If ParameterExist(parameters1, "ING. SISTEMAS", Param) Then
        Set strParam1 = parameters1.ITEM(part1.Name & "\ING. SISTEMAS")
        strParam1.Value = N_SIS & "_" & ESTADO_SIS
    Else
        Set strParam1 = parameters1.CreateString("ING. SISTEMAS", "")
        Dim arrayOfVariantOfBSTR3(0)
        arrayOfVariantOfBSTR3(0) = N_SIS & "_" & ESTADO_SIS
        Set strParam1Variant = strParam1
        strParam1Variant.SetEnumerateValues arrayOfVariantOfBSTR3
        strParam1.Value = N_SIS & "_" & ESTADO_SIS
    End If
    
    If ParameterExist(parameters1, "VER. RESIST.", Param) Then
        Set strParam1 = parameters1.ITEM(part1.Name & "\VER. RESIST.")
        strParam1.Value = N_RES & "_" & ESTADO_RES
    Else
        Set strParam1 = parameters1.CreateString("VER. RESIST.", "")
        Dim arrayOfVariantOfBSTR4(0)
        arrayOfVariantOfBSTR4(0) = N_RES & "_" & ESTADO_RES
        Set strParam1Variant = strParam1
        strParam1Variant.SetEnumerateValues arrayOfVariantOfBSTR4
        strParam1.Value = N_RES & "_" & ESTADO_RES
    End If
    
    If ParameterExist(parameters1, "APROBÓ", Param) Then
        Set strParam1 = parameters1.ITEM(part1.Name & "\APROBÓ")
        strParam1.Value = N_APR & "_" & ESTADO_APR
    Else
        Set strParam1 = parameters1.CreateString("APROBÓ", "")
        Dim arrayOfVariantOfBSTR5(0)
        arrayOfVariantOfBSTR5(0) = N_APR & "_" & ESTADO_APR
        Set strParam1Variant = strParam1
        strParam1Variant.SetEnumerateValues arrayOfVariantOfBSTR5
        strParam1.Value = N_APR & "_" & ESTADO_APR
    End If

    part1.Update
    
'=======================================================================================================================================================
'SI EL ARCHIVO ES UN DRAWING
'=======================================================================================================================================================
ElseIf TypeName(CATIA.ActiveDocument) = "DrawingDocument" Then

    Call Rutas("PROCESO", RUTA_SALIDA, PROY_CODE)

    Dim drawingDocument1 As DrawingDocument
    Set drawingDocument1 = CATIA.ActiveDocument
    Set parameters1 = drawingDocument1.Parameters

    'SI LA PARTE NO ESTÁ BIEN NOMBRADA SE PIDE GUARDARLA CON LA MACRO
    '================================================================
    If Len(CATIA.ActiveDocument.Name) < 20 Then
        MsgBox "El Numero de Parte no es correcto. Debe guardarlo con la Macro.", vbCritical, "Error en " & CATIA.ActiveDocument.Name
        Exit Sub
    End If

    PN = Left(CATIA.ActiveDocument.Name, intgr_N_PN)

    'SI SE TRATA DE UN CONJUNTO AUXILIAR SE OMITEN LOS PRIMEROS TRES CARÁCTERES
    '==========================================================================
    If Left(PN, 3) = "DWG" Then
        PN = Mid(CATIA.ActiveDocument.Name, intgr_POS_GRUPO, intgr_N_PN)
    End If

    'SE ASIGNA EL CSI, SI LA PARTE SE ENCUENTRA EN MUCHOS CONJUNTOS SE PIDE ASIGNAR EL CSI
    '=====================================================================================
    PN_FOR_CSI = PN
    UserForm7.Show
    
    Dim parameters33 As Parameters
    Set parameters33 = drawingDocument1.Parameters
    
    Dim strParam33 As StrParam
    Set strParam33 = parameters33.ITEM("Drawing\PROXIMO CONJUNTO")
    strParam33.Value = N_CSI
    
    'SE CUENTAN LAS REVISIONES EXISTENTES ENTRANDO A LA CARPETA DE DOC TECNICA
    '=========================================================================
    msgerror = False
    TIPO_DOC = "ZG"
    Call BuscarRev(PN, REV, msgerror, TIPO_DOC, PartProd)
    
    If msgerror = True Then
        MsgBox "Existe un error para encontrar la Revisión de este número de parte.", vbCritical
        Exit Sub
    End If
    
    REV_count = Asc(REV) - 64
    
    DRAWING_PN = Mid(drawingDocument1.Name, 1, InStr(1, drawingDocument1.Name, ".CATDrawing") - 1)
       
    Call VerResponsables(PN, REV_count, N_FAB, N_REV, N_SIS, N_RES, N_APR, ESTADO_FAB, ESTADO_REV, ESTADO_SIS, ESTADO_RES, ESTADO_APR, N_Nivel, N_Cantidad, N_Numero_Parte, N_Nro_Ord, N_Autor, N_Estado, N_Tipo, N_MATERIAL, no_resp)
    
    If no_resp = True Then
        MsgBox "Error!! La Estructura de Producto está incompleta." & vbNewLine & "Usted esta intentando sincronizar la EDICIÓN: " & REV
        Exit Sub
    End If
    
    'SI SE TRATA DE UNA REVISIÓN, SE EVITA CAMBIAR EL DISEŃADOR ORIGINAL.
    If REV = "A" Then
        Set strParam1 = parameters1.ITEM("Drawing\DISEŃO")
        strParam1.Value = UCase(Environ$("username"))
    End If

    Dim parameters2 As Parameters
    Set parameters2 = drawingDocument1.Parameters
    
    Dim strParam2 As StrParam
    Set strParam2 = parameters2.ITEM("Drawing\ING DE FAB")
    
    strParam2.Value = N_FAB & "_" & ESTADO_FAB
    
    'SI EL PN YA HA SIDO APROBADO POR EL REVISOR DE FABRICACIÓN SE OMITE INFORMAR EL ESTADO
    If ESTADO_FAB = "F" Then
        strParam2.Value = N_FAB
    End If
    
    Dim parameters3 As Parameters
    Set parameters3 = drawingDocument1.Parameters
    
    Dim strParam3 As StrParam
    Set strParam3 = parameters3.ITEM("Drawing\REVISO")
    
    strParam3.Value = N_REV & "_" & ESTADO_REV
    
    'SI EL PN YA HA SIDO APROBADO POR EL REVISOR SE OMITE INFORMAR EL ESTADO
    If ESTADO_REV = "F" Then
        strParam3.Value = N_REV
    End If
    
    Dim parameters4 As Parameters
    Set parameters4 = drawingDocument1.Parameters
    
    Dim strParam4 As StrParam
    Set strParam4 = parameters4.ITEM("Drawing\ING SIST")
    
    strParam4.Value = N_SIS & "_" & ESTADO_SIS
    
    'SI EL PN YA HA SIDO APROBADO POR EL REVISOR DE SISTEMAS SE OMITE INFORMAR EL ESTADO
    If ESTADO_SIS = "F" Then
        strParam4.Value = N_SIS
    End If
    
    Dim parameters5 As Parameters
    Set parameters5 = drawingDocument1.Parameters
    
    Dim strParam5 As StrParam
    Set strParam5 = parameters5.ITEM("Drawing\RESIST EST")
    
    strParam5.Value = N_RES & "_" & ESTADO_RES
    
    'SI EL PN YA HA SIDO APROBADO POR EL REVISOR CALCULO ESTRUCTURAL SE OMITE INFORMAR EL ESTADO
    If ESTADO_RES = "F" Then
        strParam5.Value = N_RES
    End If
    
    Dim parameters6 As Parameters
    Set parameters6 = drawingDocument1.Parameters
    
    Dim strParam6 As StrParam
    Set strParam6 = parameters6.ITEM("Drawing\APROBO")
    
    strParam6.Value = N_APR & "_" & ESTADO_APR
    
    'SI EL PN YA HA SIDO APROBADO POR EL APROBADOR SE OMITE INFORMAR EL ESTADO
    If ESTADO_APR = "F" Then
        strParam6.Value = N_APR
    End If
    
    On Error Resume Next
    
    Dim parameters34 As Parameters
    Set parameters34 = drawingDocument1.Parameters
    Dim strParam34 As StrParam
    Set strParam34 = parameters34.ITEM("Drawing\REV_" & REV)
    strParam34.Value = REV
    
    Dim parameters35 As Parameters
    Set parameters35 = drawingDocument1.Parameters
    Dim strParam35 As StrParam
    Set strParam35 = parameters35.ITEM("Drawing\IMI_" & REV)
    strParam35.Value = "XX"
    
    Dim parameters36 As Parameters
    Set parameters36 = drawingDocument1.Parameters
    Set strParam36 = parameters36.ITEM("Drawing\REVISOR_" & REV)
    strParam36.Value = UCase(Environ("username"))
    
    On Error GoTo 0
    
'=======================================================================================================================================================
'SI EL ARCHIVO ES UN PRODUCTO
'=======================================================================================================================================================
ElseIf TypeName(CATIA.ActiveDocument) = "ProductDocument" Then

    Set oseleccion = CATIA.ActiveDocument.Selection

    If oseleccion.Count = 1 Then

        On Error GoTo MensajeErrorSeleccion

        If UCase(TypeName(oseleccion.ITEM(1).Value.ReferenceProduct.Parent)) = UCase("ProductDocument") Then

            Dim product1 As Product
            Set product1 = oseleccion.ITEM(1).Value.ReferenceProduct.Parent.Product

            Dim products1 As Products
            Set products1 = product1.Products

            Set parameters1 = product1.Parameters

            PNAUX = Split(product1.Name, "_")
            PN = PNAUX(0)

            TIPO_DOC = "DD3"
            Call BuscarRev(PN, REV, msgerror, TIPO_DOC, "PRODUCTO")

            REV_count = Asc(REV) - 64

            For i = 1 To REV_count
                REV_APROBADOR_VALOR = "REV_" & Chr(64 + i)
                REV_APROBADOR = False
                If ParameterExist(parameters1, REV_APROBADOR_VALOR, Param) Then
                    REV_APROBADOR = True
                End If
            Next

            Call VerResponsables(PN, REV_count, N_FAB, N_REV, N_SIS, N_RES, N_APR, ESTADO_FAB, ESTADO_REV, ESTADO_SIS, ESTADO_RES, ESTADO_APR, N_Nivel, N_Cantidad, N_Numero_Parte, N_Nro_Ord, N_Autor, N_Estado, N_Tipo, N_MATERIAL, no_resp)

            'SI EL PARAMETRO EXISTE SE LO ACTUALIZA, SINO SE LO CREA PRIMERO Y SE LO ACTUALIZA DESPUES.
            If ParameterExist(parameters1, product1.Name & "\Masa", Param) Then
            Else
                Set dimension1 = parameters1.CreateDimension("Masa", "MASS", 0#)
            End If
            
            'SI EL PARAMETRO EXISTE SE LO ACTUALIZA, SINO SE LO CREA PRIMERO Y SE LO ACTUALIZA DESPUES.
            If ParameterExist(parameters1, product1.Name & "\Código_ATA", Param) Then
            Else
                Set stringParam1 = parameters1.CreateString("Código_ATA", "")
            End If
    
    
            If REV_count > 1 Then
                If ParameterExist(parameters1, product1.Name & "\" & REV_APROBADOR_VALOR, Param) Then
                    Set strParam1 = parameters1.ITEM(product1.Name & "\" & REV_APROBADOR_VALOR)
                    strParam1.Value = UCase(Environ("username"))
                Else
                    Set strParam1 = parameters1.CreateString(REV_APROBADOR_VALOR, "")
                    arrayOfVariantOfBSTR7(0) = UCase(Environ("username"))
                    Set strParam1Variant = strParam1
                    strParam1Variant.SetEnumerateValues arrayOfVariantOfBSTR7
                    strParam1.Value = UCase(Environ("username"))
                End If
            End If
            
            If ParameterExist(parameters1, product1.Name & "\Autor", Param) Then
                Set strParam1 = parameters1.ITEM(product1.Name & "\Autor")
                strParam1.Value = N_Autor
            Else
                Set strParam1 = parameters1.CreateString("Autor", "")
                arrayOfVariantOfBSTR1(0) = N_FAB & "_" & ESTADO_FAB
                Set strParam1Variant = strParam1
                strParam1Variant.SetEnumerateValues arrayOfVariantOfBSTR1
                strParam1.Value = N_Autor
            End If
            
            If ParameterExist(parameters1, product1.Name & "\ING. FABRIC.", Param) Then
                Set strParam1 = parameters1.ITEM(product1.Name & "\ING. FABRIC.")
                strParam1.Value = N_FAB & "_" & ESTADO_FAB
            Else
                Set strParam1 = parameters1.CreateString("ING. FABRIC.", "")
                arrayOfVariantOfBSTR1(0) = N_FAB & "_" & ESTADO_FAB
                Set strParam1Variant = strParam1
                strParam1Variant.SetEnumerateValues arrayOfVariantOfBSTR1
                strParam1.Value = N_FAB & "_" & ESTADO_FAB
            End If
            
            If ParameterExist(parameters1, product1.Name & "\REVISÓ", Param) Then
                Set strParam1 = parameters1.ITEM(product1.Name & "\REVISÓ")
                strParam1.Value = N_REV & "_" & ESTADO_REV
            Else
                Set strParam1 = parameters1.CreateString("REVISÓ", "")
                arrayOfVariantOfBSTR2(0) = N_REV & "_" & ESTADO_REV
                Set strParam1Variant = strParam1
                strParam1Variant.SetEnumerateValues arrayOfVariantOfBSTR2
                strParam1.Value = N_REV & "_" & ESTADO_REV
            End If
            
            If ParameterExist(parameters1, product1.Name & "\ING. SISTEMAS", Param) Then
                Set strParam1 = parameters1.ITEM(product1.Name & "\ING. SISTEMAS")
                strParam1.Value = N_SIS & "_" & ESTADO_SIS
            Else
                Set strParam1 = parameters1.CreateString("ING. SISTEMAS", "")
                arrayOfVariantOfBSTR3(0) = N_SIS & "_" & ESTADO_SIS
                Set strParam1Variant = strParam1
                strParam1Variant.SetEnumerateValues arrayOfVariantOfBSTR3
                strParam1.Value = N_SIS & "_" & ESTADO_SIS
            End If
            
            If ParameterExist(parameters1, product1.Name & "\VER. RESIST.", Param) Then
                Set strParam1 = parameters1.ITEM(product1.Name & "\VER. RESIST.")
                strParam1.Value = N_RES & "_" & ESTADO_RES
            Else
                Set strParam1 = parameters1.CreateString("VER. RESIST.", "")
                arrayOfVariantOfBSTR4(0) = N_RES & "_" & ESTADO_RES
                Set strParam1Variant = strParam1
                strParam1Variant.SetEnumerateValues arrayOfVariantOfBSTR4
                strParam1.Value = N_RES & "_" & ESTADO_RES
            End If
            
            If ParameterExist(parameters1, product1.Name & "\APROBÓ", Param) Then
                Set strParam1 = parameters1.ITEM(product1.Name & "\APROBÓ")
                strParam1.Value = N_APR & "_" & ESTADO_APR
            Else
                Set strParam1 = parameters1.CreateString("APROBÓ", "")
                arrayOfVariantOfBSTR5(0) = N_APR & "_" & ESTADO_APR
                Set strParam1Variant = strParam1
                strParam1Variant.SetEnumerateValues arrayOfVariantOfBSTR5
                strParam1.Value = N_APR & "_" & ESTADO_APR
            End If
            
            For i = 1 To REV_count
                IMI_VALOR = "IMI_" & Chr(64 + i)
                IMI = False
                If ParameterExist(parameters1, IMI_VALOR, Param) Then
                    IMI = True
                End If
            Next
            
            On Error GoTo 0
            
            'SE DEBE IGRESAR EL IMI (INDICE DE MODIFICACIÓN) PARA CONTINUAR, SIEMPRE SE LO PIDE POR SI SE QUIERE MODIFICARLO
            '===============================================================================================================
            Do While IMI_CHECK <> True
                IMI_CHECK = True
                imi_rev = InputBox("Introduzca el IMI correspondiente a la revisión: " & REV, "Indice de Modificación", "00")
        
                'SI SE PRESIONA 'CANCEL' SE SALE
                If StrPtr(imi_rev) = 0 Then
                    Exit Sub
                End If
        
                'SE VERIFICA QUE EL IMI SE ENCUENTRE BIEN ESCRITO
                If Len(imi_rev) <> 2 Then
                    MsgBox "El numero IMI debe estar compuesto de dos caracteres. Vuelva a intentarlo e introduzcalo correctamente.", vbCritical, "Error de formato."
                    IMI_CHECK = False
                End If
        
                'SE VERIFICA QUE EL IMI NO SEA IGUAL AL DE LA REVISIÓN ANTERIOR
                If REV <> "A" Then
                    For i = 1 To REV_count - 1
                        IMI_VALOR_ANTERIOR = "IMI_" & Chr(Asc(REV) - i)
                        If imi_rev = parameters1.ITEM(product1.Name & "\" & IMI_VALOR_ANTERIOR).ValueAsString Then
                            MsgBox "Este IMI ya existe en una revisión anterior, debe ser distinto.", vbCritical
                            IMI_CHECK = False
                            Exit For
                        End If
                    Next
                End If
                
            Loop
            
            'SE AGREGA EL IMI CORRESPONDIENTE
            '================================
            If ParameterExist(parameters1, product1.Name & "\" & IMI_VALOR, Param) Then
                Set strParam1 = parameters1.ITEM(product1.Name & "\" & IMI_VALOR)
                strParam1.Value = imi_rev
            Else
                Set strParam1 = parameters1.CreateString(IMI_VALOR, "")
                Dim arrayOfVariantOfBSTR72(0)
                arrayOfVariantOfBSTR72(0) = imi_rev
                Set strParam1Variant = strParam1
                strParam1Variant.SetEnumerateValues arrayOfVariantOfBSTR72
                strParam1.Value = imi_rev
            End If
            
            For i = 1 To REV_count
                FECHA_VALOR = "FECHA_" & Chr(64 + i)
                Fecha = False
                If ParameterExist(parameters1, product1.Name & "\" & FECHA_VALOR, Param) Then
                    Fecha = True
                End If
            Next
    
            If Fecha = True Then
            'si está creado el parámetro se evita actualizarlo sin preguntar al usuario.
            ElseIf Fecha = False Then
                Set strParam1 = parameters1.CreateString(FECHA_VALOR, "")
                Dim arrayOfVariantOfBSTR92(0)
                arrayOfVariantOfBSTR92(0) = Day(Now) & "/" & Month(Now) & "/" & Year(Now)
                Set strParam1Variant = strParam1
                strParam1Variant.SetEnumerateValues arrayOfVariantOfBSTR92
                strParam1.Value = Day(Now) & "/" & Month(Now) & "/" & Year(Now)
            End If
    
        Else
        
        GoTo MensajeErrorSeleccion
        
        End If
    
    End If

End If

Exit Sub

MensajeErrorSeleccion: MsgBox "Dentro de un producto sólo se permite seleccionar y actualizar productos." & vbNewLine & vbNewLine & _
                        "Si requiere actualizar una parte debe abrirla en una nueva ventana.", vbCritical, "Límite macro.."


End Sub

Public Function ParameterExist(ByRef ParameterCollection As Parameters, ByVal ParameterName As String, ByRef OutputParameter As Parameter) As Boolean
    On Error Resume Next
    Err.Clear
    Set OutputParameter = ParameterCollection.ITEM(ParameterName)
    If Err.Number = 0 Then
        ParameterExist = True
    Else
        ParameterExist = False
    End If
    On Error GoTo 0
End Function

Sub VerResponsables(N_PARTE, REV_CONT, N_FAB, N_REV, N_SIS, N_RES, N_APR, ESTADO_FAB, ESTADO_REV, ESTADO_SIS, ESTADO_RES, ESTADO_APR, N_Nivel, N_Cantidad, N_Numero_Parte, N_Nro_Ord, N_Autor, N_Estado, N_Tipo, N_MATERIAL, no_resp)

Call PROYECTO(PROY_CODE, PROYS, ARM_SYS)

Call Columnas_EP(ARR_COLUMNAS, COL_LIMITE, PROY_CODE)

Set OBJXL = CreateObject("Excel.Application")

Call Rutas("ESTRUCTURA", RUTA_SALIDA, PROY_CODE)

Datei = RUTA_SALIDA
OBJXL.Workbooks.Open FileName:=Datei, ReadOnly:=True
OBJXL.Visible = False
OBJXL.ActiveSheet.Activate

AUX_EXCEL = Split(RUTA_SALIDA, "\")

no_resp = False
N_instancias = 0
For i = 1 To 3000
    
    If i = 3000 And no_pn = False Then
        MsgBox "El numero de parte no se encuentra en la tabla de excel, revise DESIGNACIÓN y P/N." & vbNewLine & "Revise que el P/N haya sido guardado con la Macro", vbCritical
        OBJXL.Workbooks(AUX_EXCEL(UBound(AUX_EXCEL))).Close SaveChanges:=False
        Exit Sub
    End If
    
    PN_A_REVISAR = UCase(OBJXL.Worksheets(1).Cells(i, CInt(ARR_COLUMNAS(2))))
    
    If UCase(N_PARTE) = UCase(OBJXL.Worksheets(1).Cells(i, CInt(ARR_COLUMNAS(2)))) Then
                   
                   
        'SE CUENTA LA CANTIDAD DE VECES QUE FIGURA EL PN EN EL EXCEL
        N_instancias = N_instancias + 1
        
        'SE DECLARA QUE ENTRÓ (HUBO COINCIDENCIA)
        no_pn = True
        
        'SE CHECKEA SI HAY REVISORES
        N_FAB = OBJXL.Worksheets(1).Cells(i, CInt(ARR_COLUMNAS(12)))
        N_REV = OBJXL.Worksheets(1).Cells(i, CInt(ARR_COLUMNAS(14)))
        N_SIS = OBJXL.Worksheets(1).Cells(i, CInt(ARR_COLUMNAS(16)))
        N_RES = OBJXL.Worksheets(1).Cells(i, CInt(ARR_COLUMNAS(18)))
        N_APR = OBJXL.Worksheets(1).Cells(i, CInt(ARR_COLUMNAS(20)))
        N_Nivel = OBJXL.Worksheets(1).Cells(i, CInt(ARR_COLUMNAS(1)))
        N_Cantidad = OBJXL.Worksheets(1).Cells(i, CInt(ARR_COLUMNAS(9)))
        N_Numero_Parte = OBJXL.Worksheets(1).Cells(i, CInt(ARR_COLUMNAS(2)))
        N_Autor = OBJXL.Worksheets(1).Cells(i, CInt(ARR_COLUMNAS(10)))
        N_Tipo = OBJXL.Worksheets(1).Cells(i, CInt(ARR_COLUMNAS(6)))
        
        'SE CHECKEAN LOS ESTADOS EN LOS QUE SE ENCUENTRAN LAS REVISIONES
        ESTADO_FAB = OBJXL.Worksheets(1).Cells(i, CInt(ARR_COLUMNAS(13)))
        If ESTADO_FAB = "" Then
            ESTADO_FAB = "NO INICIADO"
        End If
        
        ESTADO_REV = OBJXL.Worksheets(1).Cells(i, CInt(ARR_COLUMNAS(15)))
        If ESTADO_REV = "" Then
            ESTADO_REV = "NO INICIADO"
        End If
        
        ESTADO_SIS = OBJXL.Worksheets(1).Cells(i, CInt(ARR_COLUMNAS(17)))
        If ESTADO_SIS = "" Then
            ESTADO_SIS = "NO INICIADO"
        End If
        
        ESTADO_RES = OBJXL.Worksheets(1).Cells(i, CInt(ARR_COLUMNAS(19)))
        If ESTADO_RES = "" Then
            ESTADO_RES = "NO INICIADO"
        End If
        
        ESTADO_APR = OBJXL.Worksheets(1).Cells(i, CInt(ARR_COLUMNAS(21)))
        If ESTADO_APR = "" Then
            ESTADO_APR = "NO INICIADO"
        End If

        If N_FAB = "" Or N_REV = "" Or N_SIS = "" Or N_RES = "" Or N_APR = "" Then
            MsgBox "Falta definir uno o todos los responsables revisores." & vbNewLine & vbNewLine _
            & "Por favor, defina los revisores entrando a la siguiente ruta:" & vbNewLine & vbNewLine _
            & RUTA_SALIDA, vbCritical, "Error en Tabla de diseńo: Revisar columna N°: " & i & " - REV." & REV_CONT
            OBJXL.Workbooks(AUX_EXCEL(UBound(AUX_EXCEL))).Close SaveChanges:=False
            no_resp = True
            Exit Sub
        End If
    
    End If
    
Next

OBJXL.Workbooks(AUX_EXCEL(UBound(AUX_EXCEL))).Close SaveChanges:=False

End Sub

Sub BuscarRev(PN, REV, msgerror, TIPO_DOC, PartProd)

Call PROYECTO(PROY_CODE, PROYS, ARM_SYS)

msgerror = False

Call Rutas(TIPO_DOC, RUTA_SALIDA, PROY_CODE)

For br = 1 To 10

    REV = UCase(Chr(64 + br))
    
    Err.Clear
    On Error GoTo errorDocTec
    
    If TIPO_DOC = "DD3" Then
        If PartProd = "PARTE" Then
            rutaFV = RUTA_SALIDA & TIPO_DOC & "-" & PN & "-" & REV & ".CATPart"
        ElseIf PartProd = "PRODUCTO" Then
            rutaFV = RUTA_SALIDA & TIPO_DOC & "-" & PN & "-" & REV & ".CATProduct"
        End If
    ElseIf TIPO_DOC = "ZG" Then
        rutaFV = RUTA_SALIDA & TIPO_DOC & "-" & PN & "-" & REV & ".pdf"
    ElseIf TIPO_DOC = "PD3" Then
        rutaFV = RUTA_SALIDA & TIPO_DOC & "-" & PN & "-" & REV & ".pdf"
    ElseIf TIPO_DOC = "FV" Then
        rutaFV = RUTA_SALIDA & TIPO_DOC & "-" & PN & "-" & REV & ".pdf"
    End If
    
    
    If Len(Dir(rutaFV)) = 0 Then  'si el archivo no existe se declara que esta el la revision adecuada y se sale de la subrutina
        msgerror = False
        Exit Sub
    End If

Next

errorDocTec:
MsgBox "Usted no tiene acceso a las carpetas de documentación técnica. Debe generar un requerimiento de acceso antes de generar un FV."
msgerror = True
On Error GoTo -1

End Sub

Attribute VB_Name = "A7_Cambiar_PN"
'AUTOR: SEBASTIAN ASSAIN
'NOMBRE: A7_CAMBIAR PN F50
'VERSION 2.0
'FECHA: 02/04/2020
'CAMBIOS: EL P/N SE BORRA DESPUES DE GUARDARLO CON UN NUEVO NOMBRE
'FRASE: NO PUEDES COMETER 2 VECES EL MISMO ERROR, LA SEGUNDA VEZ SERÁ POR ELECCIÓN
'DESCRIPCIÓN: ASIGNA UNA DESIGNACION A UN P/N QUE LUEGO, LA SUBRUTINA "GUARDAR", RECONOCE COMO UN NOMBRE TRANSITORIO.

Sub CATMain()
Dim Grupo As Variant
Dim Archivo_Existente As Variant
Dim Nombre_Ruta As String
Dim Nombre_Ruta_Archivo_Guardado As String
Dim Nombre_Cambio As String

Dim Reemplazo As VbMsgBoxResult
Dim Armonizado As VbMsgBoxResult
Dim Tipo_Archivo As String
Dim Nom_PartProd As String
Dim producto As Product
Dim relationsproducto1 As Relations

Dim oseleccion As Selection
Dim Instancia As String
Dim Instancia_sp As String
Dim NInst As Variant
Dim NInst_Nueva As Variant
Dim retro As Integer
Dim BuscaPunto As String
Dim InstVec() As Variant
Dim NInstVec() As Variant
Dim Cambio As Boolean

If CATIA.Documents.Count = 0 Or CATIA.Windows.Count = 0 Then
    MsgBox "Debe tener abierto al menos un documento para utilizar esta herramienta", vbCritical
    Exit Sub
End If

Call PROYECTO(PROY_CODE, PROYS, ARM_SYS)

'NUMEROS ENTEROS PARA TRABAJAR CON PART NUMBERS
'==============================================
Call Param_PN(ARR_PN, PROY_CODE)
intgr_N_PN = ARR_PN(1)
intgr_POS_GRUPO = ARR_PN(2)
'==============================================

Dim Ruta_Maquina As String
Dim Ruta_Excel As String
Dim Ruta As String
Dim Nombre_Archivo As String
Dim partDocument1 As PartDocument
Dim part1 As Part
Dim relationsparte1 As Relations
Dim BodyToRename As Body

Dim fso As Object

CATIA.StartCommand ("Clear History")

'SE VERIFICA EL TIPO DE ARCHIVO ABIERTO
'======================================
Tipo_Archivo = TypeName(CATIA.ActiveDocument)

Call Rutas("PROCESO", RUTA_SALIDA, PROY_CODE)
Ruta_Maquina = RUTA_SALIDA

Call Rutas("ESTRUCTURA", RUTA_SALIDA, PROY_CODE)
Ruta_Excel = RUTA_SALIDA

'========================================SI EL ARCHIVO ES UNA PARTE=================================================================
'===================================================================================================================================
If Tipo_Archivo = "PartDocument" Then

    '===============SE RESTRINGE EL USO A PARTES CONTENIDAS EN PRODUCTOS=============================================================================================================
    MsgBox "Debe ejecutar esta acción desde el producto que contiene esta parte." & vbNewLine & vbNewLine & "Recuerde guardar el producto contenedor al finalizar.", vbExclamation
    Exit Sub
    '================================================================================================================================================================================

'========================================SI EL ARCHIVO ES UN PRODUCTO===============================================================
'===================================================================================================================================
ElseIf Tipo_Archivo = "ProductDocument" Then

    Set oseleccion = CATIA.ActiveDocument.Selection
    
    If oseleccion.Count > 1 Then
        MsgBox "Sólo se puede cambiar de un P/N a la vez, no sea avaro.", vbCritical
        Exit Sub
    ElseIf oseleccion.Count = 0 Then
        MsgBox "Seleccione al menos una parte o un producto.", vbCritical
        Exit Sub
    End If

    i = 1
    
    If TypeName(oseleccion.ITEM(i).Value) = "Product" Then

        'SI EL DOCUMENTO A REINICIAR ES UNA PARTE
        '========================================
        If TypeName(oseleccion.ITEM(i).Value.ReferenceProduct.Parent) = "PartDocument" Then
                
            Set part1 = oseleccion.ITEM(i).Value.ReferenceProduct.Parent.Part
            Set relationsparte1 = part1.Relations
            Set BodyToRename = oseleccion.ITEM(i).Value.ReferenceProduct.Parent.Part.Bodies.ITEM(1)

            PNPB = Left(oseleccion.ITEM(i).Value.ReferenceProduct.Parent.Part.Name, intgr_N_PN)
            Grupo = Mid(part1.Name, intgr_POS_GRUPO, 1)
            
            If IsNumeric(Grupo) = False Then
                MsgBox "No se detecta el GRUPO al que pertenece la parte." & vbNewLine & vbNewLine & _
                "El numero de parte debe tener el siguiente" & vbNewLine & _
                "formato: 'PP-U-YXXXXX-XXX'" & vbNewLine & vbNewLine & "Donde 'Y' es el GRUPO de la parte.", vbCritical, "Problema con el GRUPO del PN.."
                Exit Sub
            End If
            
            Ruta = Ruta_Maquina & Grupo & "00\3D\"
            Nombre_Ruta = Ruta & part1.Name
            Nombre_Archivo = Mid(oseleccion.ITEM(i).Value.ReferenceProduct.Parent.Name, 1, InStr(1, oseleccion.ITEM(i).Value.ReferenceProduct.Parent.Name, ".CATPart") - 1)
            Nombre_Ruta_Archivo_Guardado = oseleccion.ITEM(i).Value.ReferenceProduct.Parent.FullName
            Archivo_Existente = CATIA.FileSystem.FileExists(Nombre_Ruta & ".CATPart")
            Nombre_Inicial = oseleccion.ITEM(i).Value.ReferenceProduct.Parent.Name
            Nombre_Archivo_Guardado = CATIA.FileSystem.FileExists(Nombre_Ruta_Archivo_Guardado)
            Nombre_Cambio = Ruta & part1.Name & "_CAMBIO" & ".CATPart"
            
            'SI LA PARTE ESTA LIBERADA O PRE-LIBERADA, NO DEJA CAMBIAR EL P/N
            '================================================================
            If Left(Nombre_Archivo, 3) = "DD3" Then
                MsgBox "No es posible CAMBIAR EL P/N de una parte LIBERADA.", vbCritical
                Exit Sub
            End If
            
            'SE CREA UN BACK UP DE LA PARTE EN LOS DOCUMENTOS DEL USUARIO
            '=================================================================
            Set WshShell = CreateObject("WScript.Shell")
            strDocuments = WshShell.SpecialFolders("MyDocuments")

            str_backup = strDocuments & "\BKPS CATIA"

            strFolderExists = Dir(str_backup, vbDirectory)

            If strFolderExists = "" Then
                MkDir str_backup
            Else
            End If
            
            Set fso = VBA.CreateObject("Scripting.FileSystemObject")
            destination = str_backup & "\"
            fso.CopyFile Nombre_Ruta_Archivo_Guardado, destination, True
            '=================================================================
            
            Mata = True
            
            'SE CAMBIA EL NOMBRE EN CATIA CIRCUNSTANCIALMENTE HASTA QUE SE GUARDE CORRECTAMENTE
            '==================================================================================
            Set parameters2 = oseleccion.ITEM(i).Value.ReferenceProduct.Parent.Part.Parameters
            Set parameter1 = parameters2.ITEM("Part Number")
            parameter1.ValuateFromString (part1.Name & "_CAMBIO")
            
            CATIA.DisplayFileAlerts = False
            oseleccion.ITEM(i).Value.ReferenceProduct.Parent.SaveAs (Nombre_Cambio)
            CATIA.DisplayFileAlerts = True
            
            'SI NO SE GUARDA EVITA BORRARLO. BASICO, PERO HE ESTROPEADO MUCHOS ARCHIVOS ANTES DE DARME CUENTA.
            '=================================================================================================
            If CATIA.FileSystem.FileExists(Nombre_Cambio) = False Then
                Mata = False
            End If
            
            'SI EL ARCHIVO COMIENZA POR DD3 NO SE BORRA
            '===========================================
            If Left(Nombre_Inicial, 3) = "DD3" Then
                Mata = False
            End If
            
            If Mata = True Then
                Kill (Nombre_Ruta_Archivo_Guardado)
            End If
            
            NO_CREAR = True
            
            UserForm9.Show
                    
            If NO_CREAR = True Then
                Exit Sub
            End If
            
            'SE CAMBIA EL NOMBRE EN CATIA
            '============================
            Set parameters2 = oseleccion.ITEM(i).Value.ReferenceProduct.Parent.Part.Parameters
            Set parameter1 = parameters2.ITEM("Part Number")
            parameter1.ValuateFromString (STR_PN & "_" & STR_DES)
            
            CATIA.DisplayFileAlerts = False
            Call A1_Guardar.CATMain
            CATIA.DisplayFileAlerts = True
            
        'SI EL DOCUMENTO A REINICIAR ES UN PRODUCTO
        '==========================================
        ElseIf TypeName(oseleccion.ITEM(i).Value.ReferenceProduct.Parent) = "ProductDocument" Then
                                                 
            Set producto = oseleccion.ITEM(i).Value.ReferenceProduct.Parent.Product
            Set relationsproducto1 = producto.Relations

            Grupo = Mid(producto.Name, intgr_POS_GRUPO, 1)
            Ruta = Ruta_Maquina & Grupo & "00\3D\"
            Nombre_Ruta = Ruta & producto.Name
            Nombre_Archivo = Mid(oseleccion.ITEM(i).Value.ReferenceProduct.Parent.Name, 1, InStr(1, oseleccion.ITEM(i).Value.ReferenceProduct.Parent.Name, ".CATProduct") - 1)
            Nombre_Ruta_Archivo_Guardado = oseleccion.ITEM(i).Value.ReferenceProduct.Parent.FullName
            Nombre_Inicial = oseleccion.ITEM(i).Value.ReferenceProduct.Parent.Name
            Archivo_Existente = CATIA.FileSystem.FileExists(Nombre_Ruta & ".CATProduct")
            Archivo_Existente_Previo = CATIA.FileSystem.FileExists(Nombre_Ruta_Archivo_Guardado)
            Instancia = Right(oseleccion.ITEM(i).Value.Name, 2)
            Nombre_Cambio = Ruta & producto.Name & "_CAMBIO" & ".CATProduct"
            
            'SE CREA UN BACK UP DE LA PARTE EN LOS DOCUMENTOS DEL USUARIO
            '=================================================================
            Set WshShell = CreateObject("WScript.Shell")
            strDocuments = WshShell.SpecialFolders("MyDocuments")

            str_backup = strDocuments & "\BKPS CATIA"

            strFolderExists = Dir(str_backup, vbDirectory)

            If strFolderExists = "" Then
                MkDir str_backup
            Else
            End If

            Set fso = VBA.CreateObject("Scripting.FileSystemObject")
            destination = str_backup & "\"
            fso.CopyFile Nombre_Ruta_Archivo_Guardado, destination, True
            '=================================================================
            
            'SE CAMBIA EL NOMBRE EN CATIA CIRCUNSTANCIALMENTE HASTA QUE SE GUARDE CORRECTAMENTE
            '==================================================================================
            oseleccion.ITEM(i).Value.ReferenceProduct.PartNumber = producto.Name & "_CAMBIO"
            
            CATIA.DisplayFileAlerts = False
            oseleccion.ITEM(i).Value.ReferenceProduct.Parent.SaveAs (Nombre_Cambio)
            CATIA.DisplayFileAlerts = True
            
            'SI EL ARCHIVO COMIENZA POR DD3 NO SE BORRA
            '===========================================
            If Left(Nombre_Inicial, 3) = "DD3" Then
                Exit Sub
            End If
            
            Kill (Nombre_Ruta_Archivo_Guardado)
            
            NO_CREAR = True
            
            UserForm9.Show
                    
            If NO_CREAR = True Then
                Exit Sub
            End If
            
            'SE CAMBIA EL NOMBRE EN CATIA
            '============================
            oseleccion.ITEM(i).Value.ReferenceProduct.PartNumber = STR_PN & "_" & STR_DES
            
            CATIA.DisplayFileAlerts = False
            Call A1_Guardar.CATMain
            CATIA.DisplayFileAlerts = True
            
        End If
    End If

CATIA.ActiveDocument.Save

End If


End Sub

Attribute VB_Name = "A8_Generar_PDT"
'AUTOR: SEBASTIAN ASSAIN
'NOMBRE: A8_Generar_PDT
'VERSION 1.0
'FECHA: 02/04/2020
'CAMBIOS:SE LINKEA CON SUBRUTINA CON RUTAS DE PROYECTO
'FRASE:
'DESCRIPCIÓN: GENERA ARCHIVOS PARA SER REVISADOS Y ENVIA UNA TAREA AL RESPONSABLE DE LA REVISIÓN.
Public opc As Variant
Public ATA_CODE As Variant
Public PROT_SUP As Variant
Public IdxSet As Integer
Public ARR_USUARIOS() As Variant

Sub CATMain()

'SE HACE UN BACK-UP DE LA ESTRUCTURA DE PRODUCTO
'===============================================
Dim fso As Object
Set fso = VBA.CreateObject("Scripting.FileSystemObject")
Call PROYECTO(PROY_CODE, PROYS, ARM_SYS)

Call Rutas("ESTRUCTURA", RUTA_SALIDA, PROY_CODE)
SourcePath = RUTA_SALIDA
Call Rutas("BACKUP", RUTA_SALIDA, PROY_CODE)
DestinationPath = RUTA_SALIDA
Call fso.CopyFile(SourcePath, DestinationPath)


'SE CARGA LA LIBRERÍA PARA TRABAJAR CON POWER POINT
'==================================================
Call LibreriasDisponibles(1)

'SI NO EXISTE NINGUN DOCUMENTO ABIERTO SE EVITA QUE LA MACRO DEVUELVA UN ERROR
'=============================================================================
If CATIA.Documents.Count = 0 Or CATIA.Windows.Count = 0 Then
    MsgBox "Debe tener abierto al menos un documento para utilizar esta herramienta", vbCritical
    Call LibreriasDisponibles(2)
    Exit Sub
End If

'NUMEROS ENTEROS PARA TRABAJAR CON PART NUMBERS
'==============================================
Call Param_PN(ARR_PN, PROY_CODE)
intgr_N_PN = ARR_PN(1)
intgr_POS_GRUPO = ARR_PN(2)
'==============================================

Dim activeviewer As Viewer
Set activeviewer = CATIA.ActiveWindow.activeviewer

Dim foto As String
Dim oAnnotationSets As AnnotationSets
Dim oAnnotationSet As AnnotationSet
Dim oAnnotations As Annotations
Dim oAnnotation As Annotation
Dim oSel As Selection
Dim visProperties1 As INFITF.VisPropertySet
Dim Param As Parameter
Dim parameters1 As Parameters
Dim MAT_REV(10, 3) As Variant
Dim RUTA_ORIGINAL As String

Set oSettings = CATIA.SettingControllers

'AQUI SE DEBE INSERTAR UN CÓDIGO QUE PERMITA UNICAR EL ARCHIVO EN UNA RUTA ESPECIFICA
'====================================================================================
Call Rutas("PDT", RUTA_SALIDA, PROY_CODE)

PathFile = RUTA_SALIDA

STR_REV_IMI = "OK"
STR_REV_FECHA = "OK"
STR_REV_REV = "OK"

'=======================================================================================================================================================
'======================================================SI EL ARCHIVO ES UNA PARTE=======================================================================
'=======================================================================================================================================================
If TypeName(CATIA.ActiveDocument) = "PartDocument" Then
    
    Dim DESCAUX() As String
    
    Dim specsAndGeomWindowl As SpecsAndGeomWindow
    Set specsAndGeomWindowl = CATIA.ActiveWindow
    
    Dim viewer3Dl As Viewer3D
    Set viewer3Dl = specsAndGeomWindowl.activeviewer
    
    Dim viewpoint3Dl As Viewpoint3D
    Set viewpoint3Dl = viewer3Dl.Viewpoint3D
        
    Dim partDocument1 As PartDocument
    Set partDocument1 = CATIA.ActiveDocument
    Dim part1 As Part
    Set part1 = partDocument1.Part
    
    Set parameters1 = part1.Parameters
    
    'SE ELIMINA LA EXTENSIÓN ".CATPart"
    '==================================
    'FileName = Left(CATIA.ActiveDocument.Name, Len(CATIA.ActiveDocument.Name) - 8)
    
    RUTA_ORIGINAL = partDocument1.FullName

    FileName = Left(part1.Name, intgr_N_PN)
    DESCAUX = Split(part1.Name, "_")
    PN = DESCAUX(0)
    DESC = DESCAUX(1)
    
    REV = "A"
    
    TIPO_DOC = "DD3"
    
    'SI EL ARCHIVO ESTÁ LIBERADO, SOLO SE BUSCA QUE LOS PARÁMETROS DE LA 'REV A' ESTEN BIEN Y SE PERMITE HACER EL PDT.
    If Left(partDocument1.Name, 2) <> "DD" And Left(partDocument1.Name, 2) <> "DF" Then
        Call BuscarRev(PN, REV, msgerror, TIPO_DOC)
    End If
    
    If msgerror = True Then
        'MsgBox "salta el msgerror (PDT)"
        Call LibreriasDisponibles(2)
        Exit Sub
    End If
    
    INGFAB = False
    REVISO = False
    INGSIST = False
    VERRES = False
    APROB = False
    
    Dim arr3() As Variant
    ReDim arr3(0 To 6)
    
    Call ParameterExist(parameters1, "CSI", Param)

    'SE ANALIZA SI HAY ERROR, SI LO HAY SIGNIFICA QUE EL CSI NO ESTÁ ASIGNADO
    '========================================================================
    On Error Resume Next
    Err.Clear
    N_CSI = Param.ValueAsString

    If Err.Number <> 0 Or Param.ValueAsString = "" Then
        Sincronizar = MsgBox("Falta asignar el conjunto inmediato superior (CSI)." & vbNewLine & vbNewLine & "Desea sincronizar la parte con la estructura de producto?", vbCritical + vbYesNo, "Falta CSI")
        If Sincronizar = vbYes Then
            Call A6_Sincronizar.CATMain
        ElseIf Sincronizar = vbNo Then
            Exit Sub
        End If
    End If

    Err.Clear
    
    Call ParameterExist(parameters1, "CSI", Param)
    N_CSI = Param.ValueAsString
    
    If Err.Number <> 0 Or Param.ValueAsString = "" Then
        MsgBox "Falta asignar el conjunto inmediato superior (CSI) dentro de la Estructura de Producto del proyecto.", vbCritical
        Exit Sub
    End If
    
    On Error GoTo 0
    
    
    'SE ANALIZA SI LA PARTE YA TIENE EL CONJUNTO INMEDIATO SUPERIOR ASIGNADO
    '=======================================================================
    If ParameterExist(parameters1, "CSI", Param) Then
        arr3(6) = Param.ValueAsString
    Else
        MsgBox "Falta asignar el parámetro CSI (Conjunto Inmediato Superior. Sincronice la parte e intentelo nuevamente.", vbCritical
        Call LibreriasDisponibles(2)
        Exit Sub
    End If

    'SE ANALIZA SI LA PARTE YA TIENE LOS RESPONSABLES ASIGNADOS
    '==========================================================
    If ParameterExist(parameters1, "Autor", Param) Then
        arr3(0) = Param.ValueAsString
    End If


    YA_TA = False
    If ParameterExist(parameters1, "ING. FABRIC.", Param) Then
        P_REVISOR = Param.ValueAsString
            'EL RESPONSABLE ES UNA CAMBINACIÓN DE UN USUARIO_ESTADO. SE VERIFICA QUE EL FORMATO ESTE CORRECTO.
            'SI NO ES ASÍ SE DEBE ASIGNAR NUEVAMENTE LOS RESPONSABLES.
            If InStr(Param.ValueAsString, "_") = 0 Then
                MsgBox "Actualice los responsables asignados para revisar la parte y vuelva a intentarlo!", vbExclamation
                Call LibreriasDisponibles(2)
                Exit Sub
                
            End If
        DIVISOR = Split(Param.ValueAsString, "_")
        'SI EL PRIMER REVISOR NO HA REVISADO LA PARTE (ESTO ES, ASIGNADO UNA "R" O UNA "F") SE LO DESIGNA COMO DESTINATARIO DEL MAIL.
        'SI YA A REVISADO LA PARTE SE EVITA VOLVER A ENVIARLE UN MAIL CON LA TAREA.
        If DIVISOR(1) = "NO INICIADO" Or DIVISOR(1) = "1" Or DIVISOR(1) = "2" Or DIVISOR(1) = "3" Or DIVISOR(1) = "4" Then
            REVISOR_MAIL = DIVISOR(0) & "@fadeasa.com.ar"
            YA_TA = True
        End If
        INGFAB = True
        arr3(1) = DIVISOR(0)
    End If
    
    If ParameterExist(parameters1, "REVISÓ", Param) Then
            'EL RESPONSABLE ES UNA CAMBINACIÓN DE UN USUARIO_ESTADO. SE VERIFICA QUE EL FORMATO ESTE CORRECTO.
            'SI NO ES ASÍ SE DEBE ASIGNAR NUEVAMENTE LOS RESPONSABLES.
            If InStr(Param.ValueAsString, "_") = 0 Then
                MsgBox "Actualice los responsables asignados para revisar la parte y vuelva a intentarlo!", vbExclamation
                Call LibreriasDisponibles(2)
                Exit Sub
            End If
        DIVISOR = Split(Param.ValueAsString, "_")
        'SI EL PRIMER REVISOR NO HA REVISADO LA PARTE (ESTO ES, ASIGNADO UNA "R" O UNA "F") SE LO DESIGNA COMO DESTINATARIO DEL MAIL.
        'SI YA A REVISADO LA PARTE SE EVITA VOLVER A ENVIARLE UN MAIL CON LA TAREA.
        If YA_TA = False Then
            If DIVISOR(1) = "NO INICIADO" Or DIVISOR(1) = "1" Or DIVISOR(1) = "2" Or DIVISOR(1) = "3" Or DIVISOR(1) = "4" Then
                REVISOR_MAIL = DIVISOR(0) & "@fadeasa.com.ar"
                YA_TA = True
            End If
        End If
        REVISO = True
        arr3(2) = DIVISOR(0)
    End If
    
    If ParameterExist(parameters1, "ING. SISTEMAS", Param) Then
            'EL RESPONSABLE ES UNA CAMBINACIÓN DE UN USUARIO_ESTADO. SE VERIFICA QUE EL FORMATO ESTE CORRECTO.
            'SI NO ES ASÍ SE DEBE ASIGNAR NUEVAMENTE LOS RESPONSABLES.
            If InStr(Param.ValueAsString, "_") = 0 Then
                MsgBox "Actualice los responsables asignados para revisar la parte y vuelva a intentarlo!", vbExclamation
                Call LibreriasDisponibles(2)
                Exit Sub
            End If
        DIVISOR = Split(Param.ValueAsString, "_")
        'SI EL PRIMER REVISOR NO HA REVISADO LA PARTE (ESTO ES, ASIGNADO UNA "R" O UNA "F") SE LO DESIGNA COMO DESTINATARIO DEL MAIL.
        'SI YA A REVISADO LA PARTE SE EVITA VOLVER A ENVIARLE UN MAIL CON LA TAREA.
        If YA_TA = False Then
            If DIVISOR(1) = "NO INICIADO" Or DIVISOR(1) = "1" Or DIVISOR(1) = "2" Or DIVISOR(1) = "3" Or DIVISOR(1) = "4" Then
                REVISOR_MAIL = DIVISOR(0) & "@fadeasa.com.ar"
                YA_TA = True
            End If
        End If
        INGSIST = True
        arr3(3) = DIVISOR(0)
        End If
    
    If ParameterExist(parameters1, "VER. RESIST.", Param) Then
            'EL RESPONSABLE ES UNA CAMBINACIÓN DE UN USUARIO_ESTADO. SE VERIFICA QUE EL FORMATO ESTE CORRECTO.
            'SI NO ES ASÍ SE DEBE ASIGNAR NUEVAMENTE LOS RESPONSABLES.
            If InStr(Param.ValueAsString, "_") = 0 Then
                MsgBox "Actualice los responsables asignados para revisar la parte y vuelva a intentarlo!", vbExclamation
                Call LibreriasDisponibles(2)
                Exit Sub
            End If
        DIVISOR = Split(Param.ValueAsString, "_")
        'SI EL PRIMER REVISOR NO HA REVISADO LA PARTE (ESTO ES, ASIGNADO UNA "R" O UNA "F") SE LO DESIGNA COMO DESTINATARIO DEL MAIL.
        'SI YA A REVISADO LA PARTE SE EVITA VOLVER A ENVIARLE UN MAIL CON LA TAREA.
        If YA_TA = False Then
            If DIVISOR(1) = "NO INICIADO" Or DIVISOR(1) = "1" Or DIVISOR(1) = "2" Or DIVISOR(1) = "3" Or DIVISOR(1) = "4" Then
                REVISOR_MAIL = DIVISOR(0) & "@fadeasa.com.ar"
                YA_TA = True
            End If
        End If
        VERRES = True
        arr3(4) = DIVISOR(0)
    End If
    
    If ParameterExist(parameters1, "APROBÓ", Param) Then
            'EL RESPONSABLE ES UNA CAMBINACIÓN DE UN USUARIO_ESTADO. SE VERIFICA QUE EL FORMATO ESTE CORRECTO.
            'SI NO ES ASÍ SE DEBE ASIGNAR NUEVAMENTE LOS RESPONSABLES.
            If InStr(Param.ValueAsString, "_") = 0 Then
                MsgBox "Actualice los responsables asignados para revisar la parte y vuelva a intentarlo!", vbExclamation
                Call LibreriasDisponibles(2)
                Exit Sub
            End If
        DIVISOR = Split(Param.ValueAsString, "_")
        'SI EL PRIMER REVISOR NO HA REVISADO LA PARTE (ESTO ES, ASIGNADO UNA "R" O UNA "F") SE LO DESIGNA COMO DESTINATARIO DEL MAIL.
        'SI YA A REVISADO LA PARTE SE EVITA VOLVER A ENVIARLE UN MAIL CON LA TAREA.
        If YA_TA = False Then
            If DIVISOR(1) = "NO INICIADO" Or DIVISOR(1) = "1" Or DIVISOR(1) = "2" Or DIVISOR(1) = "3" Or DIVISOR(1) = "4" Then
                REVISOR_MAIL = DIVISOR(0) & "@fadeasa.com.ar"
                YA_TA = True
            End If
        End If
        APROB = True
        arr3(5) = DIVISOR(0)
    End If
    
    'SE VERIFICA QUE ESTÉ ASIGNADO EL IMI CORRESPONDIENTE PARA LA REVISIÓN
    If Not ParameterExist(parameters1, "IMI_" & REV, Param) Then
        STR_REV_IMI = "FALTA"
    End If
    
    'SE VERIFICA QUE ESTÉ ASIGNADA AL FECHA CORRESPONDIENTE PARA LA REVISIÓN
    If Not ParameterExist(parameters1, "FECHA_" & REV, Param) Then
        STR_REV_FECHA = "FALTA"
    End If
    
    'SE VERIFICA QUE ESTÉ ASIGNADO EL RESPONSABLE CORRESPONDIENTE PARA LA REVISIÓN (EN CASO DE QUE SEA LA PRIMERA LIBERACION SE USA EL AUTOR COMO RESPONSABLE)
    If REV <> "A" Then
        If Not ParameterExist(parameters1, "REV_" & REV, Param) Then
            STR_REV_REV = "FALTA"
        End If
    End If
    
    'SE ADVIERTE AL USUARIO LA FALTA DE PARÁMETROS ESCENCIALES.
    If STR_REV_IMI = "FALTA" Or STR_REV_FECHA = "FALTA" Or STR_REV_REV = "FALTA" Then
        MsgBox "Se han encontrado los siguientes parametros faltantes, no es posible generar el PD3 o FV sin ellos:" & vbNewLine & vbNewLine & vbNewLine _
        & "[IMI_" & REV & "]=" & vbTab & vbTab & STR_REV_IMI & vbNewLine _
        & "[FECHA_" & REV & "]=" & vbTab & STR_REV_FECHA & vbNewLine _
        & "[REV_" & REV & "]=" & vbTab & vbTab & STR_REV_REV & vbNewLine & vbNewLine _
        & "Recuerde que usted está intentando generar el PD3 o el FV de la revisión " & REV & " de esta parte." & vbNewLine & vbNewLine _
        & "Corrija los errores y/o complete los datos faltantes y vuelva a intentarlo." _
        , vbCritical + vbOKOnly, "Atención! Parámetros faltantes y/o incorrectos."
        Call LibreriasDisponibles(2)
        Exit Sub
    End If
    
    'SE GENERA UNA MATRIZ DE REVISIÓN (SIEMPRE EMPIEZA POR LA REVISION A, SI LOS VALORES NO EXISTEN CARGA ESPACIOS VACIOS)
    'ESTA MATRIZ DE REVISIÓN ES PARA COMPLETAR EL CAMPO DE REVISORES EN LOS DOCUMENTOS FV.
    REV_count = Asc(REV) - 64

    On Error Resume Next
    For r = 1 To REV_count
        MAT_REV(r, 1) = parameters1.ITEM("IMI_" & Chr(r + 64)).ValueAsString  'PARAMETROIMI
        MAT_REV(r, 2) = parameters1.ITEM("FECHA_" & Chr(r + 64)).ValueAsString 'PARAMETROFECHA
        If r <> 1 Then
            MAT_REV(r, 3) = parameters1.ITEM("REV_" & Chr(r + 64)).ValueAsString 'PARAMETROREVISOR
        ElseIf r = 1 Then
            MAT_REV(r, 3) = parameters1.ITEM("Autor").ValueAsString 'PARAMETROREVISOR
        End If
    Next
    On Error GoTo 0
    
    'SI LOS RESPONSABLES NO FUERON ASIGNADOS DEBE HACERLO ANTES DE CONTINUAR
    '=======================================================================
    If INGFAB = False Or REVISO = False Or INGSIST = False Or VERRES = False Or APROB = False Then
        MsgBox "Por favor, asigne los responsables y vuelva a intentarlo.", vbInformation
        Call LibreriasDisponibles(2)
        Exit Sub
    End If
    
    'SI LA ULTIMA FECHA NO FUE ASIGNADA
    '==================================
    If MAT_REV(REV_count, 2) = "" Then
        MsgBox "Por favor, asigne una fecha de liberacón.", vbInformation
        Call LibreriasDisponibles(2)
        Exit Sub
    End If

    viewer3Dl.RenderingMode = catRenderShadingWithEdgesAndHiddenEdges
    
    Set oAnnotationSets = part1.AnnotationSets
    
    Set oSel = CATIA.ActiveDocument.Selection
    
    Dim ObjViewer3D As Viewer3D
    Set ObjViewer3D = CATIA.ActiveWindow.activeviewer

    '-------------------------------------------------------------------------------------------------------------------
    '-------------------------------------------------SE CREAN CARPETAS-------------------------------------------------
    '-------------------------------------------------------------------------------------------------------------------
    BOOL_BORRAR = False
    BOOL_ERROR = False
    STR_RUTA_PN = FileName & "\"
    STR_RUTA_PROD = N_CSI & "\"
    Call MkCarpetas(BOOL_BORRAR, PathFile, STR_RUTA_PROD, STR_RUTA_PN, REV, LOOP_N, BOOL_ERROR, RUTA_FINAL, RUTA_ULTIMO_LOOP)

    If BOOL_ERROR = True Then
        Call LibreriasDisponibles(2)
        Exit Sub
    End If
    
    '-------------------------------------------------------------------------------------------------------------------
    '-------------------------------------------------SE ASIGNA LA FECHA------------------------------------------------
    '-------------------------------------------------------------------------------------------------------------------
    Do
        n_do = n_do + 1
        FECHA_LISTO = True
        If REV_count = 1 Then
            MAT_REV(REV_count, 2) = InputBox("Por favor, asigne la fecha de liberación de la EDICIÓN: " & REV, "Fecha de Liberacion ", MAT_REV(REV_count, 2))
        Else
            MAT_REV(REV_count, 2) = InputBox("Por favor, asigne la fecha de liberacion de la EDICIÓN: " & REV, "Fecha de Revisión " & REV, MAT_REV(REV_count, 2))
        End If
        
        If StrPtr(MAT_REV(REV_count, 2)) = 0 Then
            viewer3Dl.RenderingMode = catRenderShadingWithEdgesWithoutSmoothEdges
            Call LibreriasDisponibles(2)
            On Error Resume Next
            RmDir (RUTA_ULTIMO_LOOP)
            On Error GoTo 0
            Exit Sub
        End If
        
        If Len(MAT_REV(REV_count, 2)) < 8 Then
            MsgBox "La fecha esta fuera de formato (cantidad de caracteres).", vbCritical
            FECHA_LISTO = False
        ElseIf Right(Date, 4) <> Right(MAT_REV(REV_count, 2), 4) Then
            MsgBox "La fecha esta fuera de formato (el ańo no corresponde al ańo en curso).", vbCritical
            FECHA_LISTO = False
        ElseIf InStr(MAT_REV(REV_count, 2), "/") = 0 Then
            MsgBox "La fecha esta fuera de formato (los separadores deben ser '/').", vbCritical
            FECHA_LISTO = False
        End If
        
        If n_do > 20 Then
            MsgBox "Todos los intentos de asignar fecha fueron fallidos, no se creo el documento.", vbCritical
            Call LibreriasDisponibles(2)
            Exit Sub
        End If

        Set strParam1 = parameters1.ITEM(part1.Name & "\FECHA_" & REV)
        strParam1.Value = MAT_REV(REV_count, 2)
    
    Loop While FECHA_LISTO = False
    
    '-------------------------------------------------------------------------------------------------------------------
    '--------------------------------------------SE CHEQUEAN PARAMETROS-------------------------------------------------
    '-------------------------------------------------------------------------------------------------------------------

    Call Param_Check(REV)

    '-------------------------------------------------------------------------------------------------------------------
    '-----------------------------------------------ASIGNACIÓN DE ATA---------------------------------------------------
    '-------------------------------------------------------------------------------------------------------------------
    B_ATA = ParameterExist(parameters1, "Código_ATA", Param)
    
    If B_ATA = True And Param.ValueAsString <> "" Then
        'si el parámetro existe y tiene un valor asignado entonces no se hace nada
        ATA_CODE = Param.ValueAsString
    ElseIf B_ATA = True And Param.ValueAsString = "" Then
        'si el parámetro existe, pero estŕ vacěo
        UserForm5.Show
        If opc = -1 Then
            viewer3Dl.RenderingMode = catRenderShadingWithEdgesWithoutSmoothEdges
            Call LibreriasDisponibles(2)
            On Error Resume Next
            RmDir (RUTA_ULTIMO_LOOP)
            On Error GoTo 0
            Exit Sub
        End If
        Set strParam1 = parameters1.ITEM(part1.Name & "\Código_ATA")
        strParam1.Value = ATA_CODE
    ElseIf B_ATA = False Then
        'si el parámetro no existe
        UserForm5.Show
        If opc = -1 Then
            viewer3Dl.RenderingMode = catRenderShadingWithEdgesWithoutSmoothEdges
            Call LibreriasDisponibles(2)
            On Error Resume Next
            RmDir (RUTA_ULTIMO_LOOP)
            On Error GoTo 0
            Exit Sub
        End If
        Set strParam1 = parameters1.CreateString("Código_ATA", "")
        Dim arrayOfVariantOfBSTR9(0)
        arrayOfVariantOfBSTR9(0) = ATA_CODE
        Set strParam1Variant = strParam1
        strParam1Variant.SetEnumerateValues arrayOfVariantOfBSTR9
        strParam1.Value = ATA_CODE
    End If
    
    '-------------------------------------------------------------------------------------------------------------------
    '-------------------------------------ASIGNACIÓN DE PROTECCION SUPERFICIAL------------------------------------------
    '-------------------------------------------------------------------------------------------------------------------
    P_SUP = ParameterExist(parameters1, "Protección_Sup.", Param)
    
    If P_SUP = True And Param.ValueAsString <> "" Then
        'si el parámetro existe y tiene un valor asignado entonces no se hace nada
        PROT_SUP = Param.ValueAsString
    ElseIf P_SUP = True And Param.ValueAsString = "" Then
        'si el parámetro existe, pero estŕ vacěo
        UserForm6.Show
        If opc = -1 Then
            viewer3Dl.RenderingMode = catRenderShadingWithEdgesWithoutSmoothEdges
            Call LibreriasDisponibles(2)
            On Error Resume Next
            RmDir (RUTA_ULTIMO_LOOP)
            On Error GoTo 0
            Exit Sub
        End If
        Set strParam1 = parameters1.ITEM(part1.Name & "\Protección_Sup.")
        strParam1.Value = PROT_SUP
    ElseIf P_SUP = False Then
        'si el parámetro no existe
        UserForm6.Show
        If opc = -1 Then
            viewer3Dl.RenderingMode = catRenderShadingWithEdgesWithoutSmoothEdges
            Call LibreriasDisponibles(2)
            On Error Resume Next
            RmDir (RUTA_ULTIMO_LOOP)
            On Error GoTo 0
            Exit Sub
        End If
        Set strParam1 = parameters1.CreateString("Protección_Sup.", "")
        Dim arrayOfVariantOfBSTR32(0)
        arrayOfVariantOfBSTR32(0) = PROT_SUP
        Set strParam1Variant = strParam1
        strParam1Variant.SetEnumerateValues arrayOfVariantOfBSTR32
        strParam1.Value = PROT_SUP
    End If
     
    'BUSCA EL PRIMER SET DE ANOTACIONES
    '==================================
    Set oAnnotationSets = part1.AnnotationSets
    
    On Error Resume Next

    Dim AnnoSet1 As AnnotationSet
    Set AnnoSet1 = oAnnotationSets.ITEM(1)

    If Err.Number = 0 Then
    
        On Error GoTo 0
    
        CATIA.StartCommand "Specifications"
        CATIA.StartCommand "Compass"
    
        'CUENTA EL NUMERO DE CAPTURAS
        '============================
        NumberCaptures = AnnoSet1.Captures.Count
        'MsgBox "Numero de anotaciones:" & oAnnotationSets.Count & " Numero de capturas: " & NumberCaptures
        
        Dim arr() As Variant
        ReDim arr(0 To NumberCaptures)
        Dim arr2() As Variant
        ReDim arr2(0 To NumberCaptures)
        
        'SI ESTÁ ACTIVADO, SE DESACTIVA EL Z-BUFFER PARA PREVENIR QUE LAS LINEAS DE COTAS QUEDEN OCULTAS DENTRO DEL BODY.
        '===============================================================================================================
        Set mySettingControllers = CATIA.SettingControllers
        Set MyVisSetting = mySettingControllers.ITEM("CATVizVisualizationSettingCtrl")
        If MyVisSetting.AllZBufferElementMode Then
            MyVisSetting.AllZBufferElementMode = False
        Else
            MyVisSetting.AllZBufferElementMode = True
        End If
        '================================================================================================================
            
            'LOOP A TRAVES DE LAS CAPTURAS
            '=============================
            For j = 1 To NumberCaptures
                
                On Error Resume Next
                'MUESTRA LA CAPTURA
                '==================
                Set CurrentCapture = AnnoSet1.Captures.ITEM(j)
                CurrentCapture.DisplayCapture
                
                On Error GoTo 0
                'SETEA LA CAPTURA j PARA EDITARLA Y GUARDAR LA IMAGEN
                '====================================================
                Dim sCapSel As Selection
                Set sCapSel = CATIA.ActiveDocument.Selection
                sCapSel.Clear
                sCapSel.Add CurrentCapture
                
                     
                'CATIA.RefreshDisplay = True
                'AppActivate "CATIA V5"
                'Application.Wait Now + TimeValue("00:05:00")
                'SendKeys "c: Activate" + Chr(13), True
                'Application.Wait Now + TimeValue("00:05:00")
                CATIA.RefreshDisplay = True
                
        
                'SE MUESTRA EL NOMBRE DE LA CAPTURA
                '==================================
                CaptureName = CurrentCapture.Name
                'MsgBox "The activated capture is: " & CaptureName
                CATIA.RefreshDisplay = True
                

                'SE AGREGA LA VISTA A LA SELECCIÓN
                '=================================
                Dim sSelView As Selection
                Set sSelView = CATIA.ActiveDocument.Selection
                sSelView.Add oAnnotationSets.ITEM(1)
                
                'SE BUSCA LA VISTA QUE COINCIDA CON EL NOMBRE DE LA CAPTURA
                sSelView.Search "Name = " & CaptureName & ", sel"
            
                'CUENTA LA CANTIDAD DE VISTAS ENCONTRADAS
                '========================================
                Dim viewFound As Integer
                viewFound = sSelView.Count
                
                    'SI EXISTEN VARIAS VISTAS COINCIDENTES SE AVISA
                    '==============================================
                    If viewFound > 1 Then
                        MsgBox "El número de vistas encontrados es: " & viewFound
                        sSelection2.Clear
                    Else
                        UserForm4.Caption = "Captura: " & CaptureName
                        UserForm4.Show
                    End If
                    
                If opc = 0 Then
                    viewer3Dl.RenderingMode = catRenderShadingWithEdgesAndHiddenEdges
                ElseIf opc = 1 Then
                    viewer3Dl.RenderingMode = catRenderShadingWithEdgesWithoutSmoothEdges
                ElseIf opc = 2 Then
                    viewer3Dl.RenderingMode = catRenderHiddenLinesRemoval
                ElseIf opc = -1 Then
                    GoTo Saltar_Abortar
                End If
            
                'SE CAMBIA EL COLOR DEL FONDO
                '============================
                Dim MyViewer
                Dim bkcolor(2)
                Dim bkcolor2(2)
                
                bkcolor2(0) = 1
                bkcolor2(1) = 1
                bkcolor2(2) = 1
                
                Set MyViewer = CATIA.ActiveWindow.activeviewer
                
                MyViewer.GetBackgroundColor bkcolor
                
                'MsgBox bkcolor(0) & ", " & bkcolor(1) & ", " & bkcolor(2)
                
                MyViewer.PutBackgroundColor bkcolor2
                
                '---------------------------------------
                'SE RECORRE TODO EL ARBOL DE ANOTACIONES
                '=======================================
                For IdxSet = 1 To oAnnotationSets.Count
                    Set oAnnotationSet = oAnnotationSets.ITEM(IdxSet)
                    Set oAnnotations = oAnnotationSet.Annotations
                    For IdxAnnot = 1 To oAnnotations.Count
                    
                        'SE CAMBIA EL COLOR DE CADA ANOTACION
                        '====================================
                        Set oAnnotation = oAnnotations.ITEM(IdxAnnot)
                        If Not oAnnotation Is Nothing Then
                            With oSel
                                .Clear
                                .Add oAnnotation
                                Call .VisProperties.SetVisibleColor(0, 0, 0, 0)
                            End With
                            oAnnotation.ModifyVisu
                        End If
                    Next
                Next
                
                
                oSel.Clear
                
                foto = RUTA_ULTIMO_LOOP & CaptureName & ".bmp"
                
                'SI LA ITERACIÓN SE ENCUENTRA EN LA CAPTURA 'ALL', Y SE GENERA EL CATPART AUXILIAR Y SE GUARDA EN LA CARPETA DE PDT
                '==================================================================================================================
                If Right(CaptureName, 4) = "ALL " Or Right(CaptureName, 3) = "ALL" Then
                    HAY_NONE = False
                    For p = 0 To NumberCaptures
                        If Right(arr2(p), 5) = "NONE " Or Right(arr2(p), 4) = "NONE" Then
                        HAY_NONE = True
                        End If
                    Next
                    If HAY_NONE = True Then
                        CATIA.DisplayFileAlerts = False
                        On Error Resume Next
                        
                        'SE COPIA EL ARCHIVO A LA CARPETA PDT
                        '=======================================================================================================
                        part1.Update
                        partDocument1.Save
                        destination = RUTA_ULTIMO_LOOP & "PD3-" & PN & "-" & REV & ".CATPart"
                        fso.CopyFile RUTA_ORIGINAL, destination, True
                        '=======================================================================================================

                        On Error GoTo 0
                        CATIA.DisplayFileAlerts = True
                    Else
                        MsgBox "No se puede generar el archivo debido a que no existe captura 'NONE'.", vbCritical
                    End If
                End If

                arr2(j) = CaptureName
                arr(j) = foto
                Call activeviewer.CaptureToFile(catCaptureFormatBMP, foto)
        
                MyViewer.PutBackgroundColor bkcolor
        
            Next 'j

Saltar_Abortar:
        
        CATIA.StartCommand "Specifications"
        CATIA.StartCommand "Compass"
        viewer3Dl.RenderingMode = catRenderShadingWithEdgesWithoutSmoothEdges
        
        If opc <> -1 Then
            If msgerror = False Then 'si el usuario no tiene acceso a las carpetas publicas no se permite gernerar un FV
                CrearFV = MsgBox("Desea crear el FV del P/N:" & vbNewLine & part1.Name & " ?", vbYesNo + vbQuestion)
                If CrearFV = vbYes Then
                    Capture_folder = RUTA_ULTIMO_LOOP & "FV-" & PN & "-" & REV
                    Call PPTSub(arr, arr2, arr3, NumberCaptures, Capture_folder, PN, DESC, REV, MAT_REV, ATA_CODE)
                ElseIf CrearFV = vbNo Then
                    'SE BORRAN TODAS LAS IMAGENES CREADAS.
                    For i = 1 To NumberCaptures
                        If arr(i) <> "" Then
                            Kill arr(i)
                        End If
                        On Error Resume Next
                        RmDir (RUTA_ULTIMO_LOOP)
                        On Error GoTo 0
                    Next
                End If
            End If
        Else

            For i = 1 To NumberCaptures
                If arr(i) <> "" Then
                    Kill arr(i)
                End If
'                On Error Resume Next
'                RmDir (PathFile & FileName & "\LOOP_" & LOOP_N)
'                On Error GoTo 0
            Next
            
            Call Reset_CAPTURAS(part1.AnnotationSets, CATIA.ActiveDocument.Selection, sCapSel, AnnoSet1)
            
            RmDir (RUTA_ULTIMO_LOOP)
            MsgBox "El archivo no ha sido generado.", vbCritical
            Call LibreriasDisponibles(2)
            Exit Sub
        End If
    Else
        MsgBox "No es posible pre-liberar la parte ya que la misma está incompleta." & vbNewLine & vbNewLine & "(1) Revise que tenga anotaciones" _
        & vbNewLine & "(2) Revise que esten asignados los revisores", vbCritical
        Call LibreriasDisponibles(2)
        Exit Sub
    End If
        
    'SE RESETEA LA NAVEGACIÓN POR LAS CAPTURAS
    Call Reset_CAPTURAS(part1.AnnotationSets, CATIA.ActiveDocument.Selection, sCapSel, AnnoSet1)
    
    'SE CREA EL RÓTULO COMO TXT
    Call CreaRotulo(arr3, RUTA_ULTIMO_LOOP, PN, DESC, REV, MAT_REV, REV_count)
    
    'SE ASIGNA EL E-MAIL DEL REVISOR
    If YA_TA = False Then
        If ParameterExist(parameters1, "ING. FABRIC.", Param) Then
            DIVISOR = Split(Param.ValueAsString, "_")
            REVISOR_MAIL = DIVISOR(0) & "@fadeasa.com.ar"
        End If
    Else
        Err.Clear
        On Error Resume Next
        DIVISOR = Split(REVISOR_MAIL, "_")
        REVISOR_MAIL = DIVISOR(0)
    End If
    
    'SI HAY UN PROBLEMA CON EL REVISOR NO SE PERMITE GENERAR EL ARCHIVO
    If Err.Number <> 0 Then
        MsgBox "Los revisores no estan cargados correctamente." & vbNewLine & vbNewLine & "Por favor, revise su PN y el Excel y vuelva a intentarlo", vbCritical, PN
        opc = -1
        GoTo Saltar_Abortar
    End If

    Tareas = InputBox("Usted va a colocar en circuito de revisión el P/N:" & vbNewLine & part1.Name & vbNewLine & vbNewLine & _
    "Desea enviar la tarea al primer revisor?" & vbNewLine & REVISOR_MAIL & vbNewLine & vbNewLine & "Link de Referencia:", "Enviar Tarea a primer corrector.", RUTA_ULTIMO_LOOP)

    If StrPtr(Tareas) = 0 Then
        MsgBox "La tarea no ha sido enviada.", vbInformation
    Else
        Call EnviarTarea(REVISOR_MAIL, part1.Name, intgr_N_PN, RUTA_ULTIMO_LOOP)
    End If
 
    part1.Update
    partDocument1.Save

    '=======================================================================================================================================================
    '========================================================SI EL ARCHIVO ES UN PRODUCTO===================================================================
    '=======================================================================================================================================================
ElseIf TypeName(CATIA.ActiveDocument) = "ProductDocument" Then
    
    Set oseleccion = CATIA.ActiveDocument.Selection
    
    Set productDocument1 = oseleccion.ITEM(1).Value.ReferenceProduct.Parent
        
    Dim product1 As Product
    Set product1 = oseleccion.ITEM(1).Value.ReferenceProduct.Parent.Product

    Dim products1 As Products
    Set products1 = product1.Products

    Set parameters1 = product1.Parameters
    
    RUTA_ORIGINAL = productDocument1.FullName

    FileName = Left(product1.Name, intgr_N_PN)
    DESCAUX = Split(product1.Name, "_")
    PN = DESCAUX(0)
    DESC = DESCAUX(1)
    
    REV = "A"
    
    TIPO_DOC = "DD3"
    
    'SI EL ARCHIVO ESTÁ LIBERADO, SOLO SE BUSCA QUE LOS PARÁMETROS DE LA 'REV A' ESTEN BIEN Y SE PERMITE HACER EL PDT.
    If Left(productDocument1.Name, 2) <> "DD" And Left(productDocument1.Name, 2) <> "DF" Then
        Call BuscarRev(PN, REV, msgerror, TIPO_DOC)
    End If
    
    'SE VERIFICA QUE ESTÉ ASIGNADO EL IMI CORRESPONDIENTE PARA LA REVISIÓN
    If Not ParameterExist(parameters1, product1.Name & "\IMI_" & REV, Param) Then
        STR_REV_IMI = "FALTA"
    End If
    
    'SE VERIFICA QUE ESTÉ ASIGNADA AL FECHA CORRESPONDIENTE PARA LA REVISIÓN
    If Not ParameterExist(parameters1, product1.Name & "\FECHA_" & REV, Param) Then
        STR_REV_FECHA = "FALTA"
    End If
    
    'SE VERIFICA QUE ESTÉ ASIGNADO EL RESPONSABLE CORRESPONDIENTE PARA LA REVISIÓN (EN CASO DE QUE SEA LA PRIMERA LIBERACION SE USA EL AUTOR COMO RESPONSABLE)
    If REV <> "A" Then
        If Not ParameterExist(parameters1, "REV_" & REV, Param) Then
            STR_REV_REV = "FALTA"
        End If
    End If
    
    'SE ADVIERTE AL USUARIO LA FALTA DE PARÁMETROS ESCENCIALES.
    If STR_REV_IMI = "FALTA" Or STR_REV_FECHA = "FALTA" Or STR_REV_REV = "FALTA" Then
        MsgBox "Se han encontrado los siguientes parametros faltantes, no es posible generar el PD3 o FV sin ellos:" & vbNewLine & vbNewLine & vbNewLine _
        & "[IMI_" & REV & "]=" & vbTab & vbTab & STR_REV_IMI & vbNewLine _
        & "[FECHA_" & REV & "]=" & vbTab & STR_REV_FECHA & vbNewLine _
        & "[REV_" & REV & "]=" & vbTab & vbTab & STR_REV_REV & vbNewLine & vbNewLine _
        & "Recuerde que usted está intentando generar el PD3 o el FV de la revisión " & REV & " de esta parte." & vbNewLine & vbNewLine _
        & "Corrija los errores y/o complete los datos faltantes y vuelva a intentarlo." _
        , vbCritical + vbOKOnly, "Atención! Parámetros faltantes y/o incorrectos."
        Exit Sub
    End If

    'SE GENERA UNA MATRIZ DE REVISIÓN (SIEMPRE EMPIEZA POR LA REVISION A, SI LOS VALORES NO EXISTEN CARGA ESPACIOS VACIOS)
    'ESTA MATRIZ DE REVISIÓN ES PARA COMPLETAR EL CAMPO DE REVISORES EN LOS DOCUMENTOS FV.
    REV_count = Asc(REV) - 64

    On Error Resume Next
    For r = 1 To REV_count
        MAT_REV(r, 1) = parameters1.ITEM(product1.Name & "\IMI_" & Chr(r + 64)).ValueAsString 'PARAMETROIMI
        MAT_REV(r, 2) = parameters1.ITEM(product1.Name & "\FECHA_" & Chr(r + 64)).ValueAsString 'PARAMETROFECHA
        If r <> 1 Then
            MAT_REV(r, 3) = parameters1.ITEM(product1.Name & "\REV_" & Chr(r + 64)).ValueAsString 'PARAMETROREVISOR
        ElseIf r = 1 Then
            MAT_REV(r, 3) = parameters1.ITEM(product1.Name & "\Autor").ValueAsString 'PARAMETROREVISOR
        End If
    Next
    On Error GoTo 0

    '-------------------------------------------------------------------------------------------------------------------
    '-------------------------------------------------SE ASIGNA LA FECHA------------------------------------------------
    '-------------------------------------------------------------------------------------------------------------------
    Do
        n_do = n_do + 1
        FECHA_LISTO = True
        If REV_count = 1 Then
            MAT_REV(REV_count, 2) = InputBox("Por favor, asigne la fecha de liberación de la EDICIÓN: " & REV, "Fecha de Liberacion ", MAT_REV(REV_count, 2))
        Else
            MAT_REV(REV_count, 2) = InputBox("Por favor, asigne la fecha de liberacion de la EDICIÓN: " & REV, "Fecha de Revisión " & REV, MAT_REV(REV_count, 2))
        End If
        
        If StrPtr(MAT_REV(REV_count, 2)) = 0 Then
            viewer3Dl.RenderingMode = catRenderShadingWithEdgesWithoutSmoothEdges
            Call LibreriasDisponibles(2)
            On Error Resume Next
            RmDir (RUTA_ULTIMO_LOOP)
            On Error GoTo 0
            Exit Sub
        End If
        
        If Len(MAT_REV(REV_count, 2)) < 8 Then
            MsgBox "La fecha esta fuera de formato (cantidad de caracteres).", vbCritical
            FECHA_LISTO = False
        ElseIf Right(Date, 4) <> Right(MAT_REV(REV_count, 2), 4) Then
            MsgBox "La fecha esta fuera de formato (el ańo no corresponde al ańo en curso).", vbCritical
            FECHA_LISTO = False
        ElseIf InStr(MAT_REV(REV_count, 2), "/") = 0 Then
            MsgBox "La fecha esta fuera de formato (los separadores deben ser '/').", vbCritical
            FECHA_LISTO = False
        End If
        
        If n_do > 20 Then
            MsgBox "Todos los intentos de asignar fecha fueron fallidos, no se creo el documento.", vbCritical
            Call LibreriasDisponibles(2)
            Exit Sub
        End If

        Set strParam1 = parameters1.ITEM(product1.Name & "\FECHA_" & REV)
        strParam1.Value = MAT_REV(REV_count, 2)
    
    Loop While FECHA_LISTO = False

    Call Param_Check(REV)
          
    'SE VERIFICA SI EL DIRECTORIO HA SIDO CREADO
    '============================================
        'SI NO HA SIDO CREADO LA CREA
        '============================
        If Dir(UCase(PathFile & FileName), vbDirectory) = "" Then
            MkDir (UCase(PathFile & FileName))
            MsgBox "Usted ha creado la siguiente ruta: " & vbNewLine & vbNewLine & PathFile & FileName, vbOKOnly + vbExclamation, "Atención!"
        End If

    '=======================================================================================================================================================
    '==================================================SI EL ARCHIVO ES UN DRAWING==========================================================================
    '=======================================================================================================================================================
ElseIf TypeName(CATIA.ActiveDocument) = "DrawingDocument" Then
    
    Dim RutaPDF As String
    Dim drawingDocument1 As DrawingDocument
    Set drawingDocument1 = CATIA.ActiveDocument
    
    'SE ELIMINA LA EXTENSIÓN ".CATProduct"
    '=====================================
    FileName = Left(CATIA.ActiveDocument.Name, intgr_N_PN)
      
    Dim relations1 As Relations
    Set relations1 = drawingDocument1.Relations
    
    Set parameters1 = drawingDocument1.Parameters
 
    INGFAB = False
    REVISO = False
    INGSIST = False
    VERRES = False
    APROB = False
    
    'SE ANALIZA SI LA PARTE YA TIENE LOS RESPONSABLES ASIGNADOS
    '==========================================================
    YA_TA = False
    If ParameterExist(parameters1, "ING DE FAB", Param) Then
        P_REVISOR = Param.ValueAsString
            'EL RESPONSABLE ES UNA CAMBINACIÓN DE UN USUARIO_ESTADO. SE VERIFICA QUE EL FORMATO ESTE CORRECTO.
            'SI NO ES ASÍ SE DEBE ASIGNAR NUEVAMENTE LOS RESPONSABLES.
        If InStr(Param.ValueAsString, "_") = 0 Then
            If Len(Param.ValueAsString) = 0 Then
                MsgBox "Actualice los responsables asignados para revisar la parte y vuelva a intentarlo!", vbExclamation
                Exit Sub
            End If
        Else
            Dim parameters2 As Parameters
            Set parameters2 = drawingDocument1.Parameters
            Dim strParam2 As StrParam
            Set strParam2 = parameters2.ITEM("Drawing\ING DE FAB")
            DIVISOR = Split(strParam2.ValueAsString, "_")
            'SI EL PRIMER REVISOR NO HA REVISADO LA PARTE (ESTO ES, ASIGNADO UNA "R" O UNA "F") SE LO DESIGNA COMO DESTINATARIO DEL MAIL.
            'SI YA A REVISADO LA PARTE SE EVITA VOLVER A ENVIARLE UN MAIL CON LA TAREA.
            If DIVISOR(1) = "NO INICIADO" Or DIVISOR(1) = "1" Or DIVISOR(1) = "2" Or DIVISOR(1) = "3" Or DIVISOR(1) = "4" Then
                REVISOR_MAIL = DIVISOR(0) & "@fadeasa.com.ar"
                YA_TA = True
            End If
            strParam2.Value = DIVISOR(0)
        End If
        INGFAB = True
    End If
    
    If ParameterExist(parameters1, "REVISO", Param) Then
        'EL RESPONSABLE ES UNA CAMBINACIÓN DE UN USUARIO_ESTADO. SE VERIFICA QUE EL FORMATO ESTE CORRECTO.
        'SI NO ES ASÍ SE DEBE ASIGNAR NUEVAMENTE LOS RESPONSABLES.
        If InStr(Param.ValueAsString, "_") = 0 Then
            If Len(Param.ValueAsString) = 0 Then
                MsgBox "Actualice los responsables asignados para revisar la parte y vuelva a intentarlo!", vbExclamation
                Exit Sub
            End If
        Else
            Dim parameters3 As Parameters
            Set parameters3 = drawingDocument1.Parameters
            Dim strParam3 As StrParam
            Set strParam3 = parameters3.ITEM("Drawing\REVISO")
            DIVISOR = Split(strParam3.ValueAsString, "_")
            'SI EL PRIMER REVISOR NO HA REVISADO LA PARTE (ESTO ES, ASIGNADO UNA "R" O UNA "F") SE LO DESIGNA COMO DESTINATARIO DEL MAIL.
            'SI YA A REVISADO LA PARTE SE EVITA VOLVER A ENVIARLE UN MAIL CON LA TAREA.
            If YA_TA = False Then
                If DIVISOR(1) = "NO INICIADO" Or DIVISOR(1) = "1" Or DIVISOR(1) = "2" Or DIVISOR(1) = "3" Or DIVISOR(1) = "4" Then
                    REVISOR_MAIL = DIVISOR(0) & "@fadeasa.com.ar"
                    YA_TA = True
                End If
            End If
            strParam3.Value = DIVISOR(0)
        End If
        REVISO = True
    End If
    
    If ParameterExist(parameters1, "ING SIST", Param) Then
            'EL RESPONSABLE ES UNA CAMBINACIÓN DE UN USUARIO_ESTADO. SE VERIFICA QUE EL FORMATO ESTE CORRECTO.
            'SI NO ES ASÍ SE DEBE ASIGNAR NUEVAMENTE LOS RESPONSABLES.
        If InStr(Param.ValueAsString, "_") = 0 Then
            If Len(Param.ValueAsString) = 0 Then
                MsgBox "Actualice los responsables asignados para revisar la parte y vuelva a intentarlo!", vbExclamation
                Exit Sub
            End If
        Else
            Dim parameters4 As Parameters
            Set parameters4 = drawingDocument1.Parameters
            Dim strParam4 As StrParam
            Set strParam4 = parameters4.ITEM("Drawing\ING SIST")
            DIVISOR = Split(strParam4.ValueAsString, "_")
            'SI EL PRIMER REVISOR NO HA REVISADO LA PARTE (ESTO ES, ASIGNADO UNA "R" O UNA "F") SE LO DESIGNA COMO DESTINATARIO DEL MAIL.
            'SI YA A REVISADO LA PARTE SE EVITA VOLVER A ENVIARLE UN MAIL CON LA TAREA.
            If YA_TA = False Then
                If DIVISOR(1) = "NO INICIADO" Or DIVISOR(1) = "1" Or DIVISOR(1) = "2" Or DIVISOR(1) = "3" Or DIVISOR(1) = "4" Then
                    REVISOR_MAIL = DIVISOR(0) & "@fadeasa.com.ar"
                    YA_TA = True
                End If
            End If
            strParam4.Value = DIVISOR(0)
        End If
        INGSIST = True
    End If
    
    If ParameterExist(parameters1, "RESIST EST", Param) Then
            'EL RESPONSABLE ES UNA CAMBINACIÓN DE UN USUARIO_ESTADO. SE VERIFICA QUE EL FORMATO ESTE CORRECTO.
            'SI NO ES ASÍ SE DEBE ASIGNAR NUEVAMENTE LOS RESPONSABLES.
            If InStr(Param.ValueAsString, "_") = 0 Then
                If Len(Param.ValueAsString) = 0 Then
                    MsgBox "Actualice los responsables asignados para revisar la parte y vuelva a intentarlo!", vbExclamation
                    Exit Sub
                End If
            Else
                Dim parameters5 As Parameters
                Set parameters5 = drawingDocument1.Parameters
                Dim strParam5 As StrParam
                Set strParam5 = parameters5.ITEM("Drawing\RESIST EST")
                DIVISOR = Split(strParam5.ValueAsString, "_")
                'SI EL PRIMER REVISOR NO HA REVISADO LA PARTE (ESTO ES, ASIGNADO UNA "R" O UNA "F") SE LO DESIGNA COMO DESTINATARIO DEL MAIL.
                'SI YA A REVISADO LA PARTE SE EVITA VOLVER A ENVIARLE UN MAIL CON LA TAREA.
                If YA_TA = False Then
                    If DIVISOR(1) = "NO INICIADO" Or DIVISOR(1) = "1" Or DIVISOR(1) = "2" Or DIVISOR(1) = "3" Or DIVISOR(1) = "4" Then
                        REVISOR_MAIL = DIVISOR(0) & "@fadeasa.com.ar"
                        YA_TA = True
                    End If
                End If
                strParam5.Value = DIVISOR(0)
            End If
        VERRES = True
    End If
    
    If ParameterExist(parameters1, "APROBO", Param) Then
            'EL RESPONSABLE ES UNA CAMBINACIÓN DE UN USUARIO_ESTADO. SE VERIFICA QUE EL FORMATO ESTE CORRECTO.
            'SI NO ES ASÍ SE DEBE ASIGNAR NUEVAMENTE LOS RESPONSABLES.
            If InStr(Param.ValueAsString, "_") = 0 Then
                If Len(Param.ValueAsString) = 0 Then
                    MsgBox "Actualice los responsables asignados para revisar la parte y vuelva a intentarlo!", vbExclamation
                    Exit Sub
                Else
                    REVISOR_MAIL = "NONE"
                End If
            Else
                Dim parameters6 As Parameters
                Set parameters6 = drawingDocument1.Parameters
                Dim strParam6 As StrParam
                Set strParam6 = parameters6.ITEM("Drawing\APROBO")
                DIVISOR = Split(strParam6.ValueAsString, "_")
                'SI EL PRIMER REVISOR NO HA REVISADO LA PARTE (ESTO ES, ASIGNADO UNA "R" O UNA "F") SE LO DESIGNA COMO DESTINATARIO DEL MAIL.
                'SI YA A REVISADO LA PARTE SE EVITA VOLVER A ENVIARLE UN MAIL CON LA TAREA.
                If YA_TA = False Then
                    If DIVISOR(1) = "NO INICIADO" Or DIVISOR(1) = "1" Or DIVISOR(1) = "2" Or DIVISOR(1) = "3" Or DIVISOR(1) = "4" Then
                        REVISOR_MAIL = DIVISOR(0) & "@fadeasa.com.ar"
                        YA_TA = True
                    End If
                End If
                strParam6.Value = DIVISOR(0)
            End If
        APROB = True
    End If
    
    If ParameterExist(parameters1, "PROXIMO CONJUNTO", Param) Then
        If Len(Param.ValueAsString) = 0 Then
            MsgBox "Falta agregar el número de 'PRÓXIMO CONJUNTO'. Asígnelo y vuelva a intentarlo.", vbExclamation
            Exit Sub
        Else
            N_CSI = Param.ValueAsString
        End If
    End If
        
        
    'SI LOS RESPONSABLES NO FUERON ASIGNADOS DEBE HACERLO ANTES DE CONTINUAR
    '=======================================================================
    If INGFAB = False Or REVISO = False Or INGSIST = False Or VERRES = False Or APROB = False Then
        MsgBox "Por favor, asigne los responsables y vuelva a intentarlo.", vbInformation
        Call LibreriasDisponibles(2)
        Exit Sub
    End If

    TIPO_DOC = "ZG"
    Call BuscarRev(FileName, REV, msgerror, TIPO_DOC)

    'SE DEBE ESTABLECER SI EL PLANO PERTENECE A UN PRODUCTO O A UNA PARTE
    '====================================================================
    'SI ES UNA PARTE DEBE EXISTIR UN 'CATPart' CON EL MISMO NUMERO DE PARTE (ESTE MÉTODO PERMITE INDEPENDIZARNOS DE LA TABLA DE EXCEL).
    Call Rutas("PROCESO", RUTA_SALIDA, PROY_CODE)

    Grupo = Mid(FileName, intgr_POS_GRUPO, 1)
    Ruta = RUTA_SALIDA & Grupo & "00\3D\"
    Modo = True 'EL MODO DEFINE SI SE BUSCA UN CATPART O UN CATPRODUCT

    'SE BUSCA SI EL ARCHIVO ESTÁ COMO CATPart EN PROCESO
    '===================================================
    BOOL_Encontro = False
    Call BuscaPalabraEnRuta(Ruta, FileName, BOOL_Encontro, Modo)
    
    'SI NO SE ENCUENTRA 'EN PROCESO' SE BUSCA SI EL CAPART ESTÁ 'LIBERADO'
    '====================================================================
    If BOOL_Encontro = False Then
        Call Rutas("DD3_ACCESS", RUTA_SALIDA, PROY_CODE)
        Call BuscaPalabraEnRuta(RUTA_SALIDA, FileName, BOOL_Encontro, Modo)
    End If
    
    'SE DEBE BUSCAR SI TIENE CATProduct, SI TIENE NO HAY PROBLEMA, SI NO TIENE EL PLANO ESTA COMPLETAMENTE DIBUJADO, PUEDE SER UNA ETIQUETA.
    '=======================================================================================================================================
    If BOOL_Encontro = False Then
        Modo = False
        Call BuscaPalabraEnRuta(Ruta, FileName, BOOL_Encontro, Modo)
        'SI NO ENCUENTRA CATProduct, AQUÍ SE TOMA LA DESICIÓN DE INIDCAR QUE ESTE PLANO ES UNA ETIQUETA Y POR LO TANTO DEBE SER TRATADO COMO UNA PARTE.
        'SI SE ENCUENTRA CATProduct, DEBIDO A COMO FUNCIONA EL CODIGO SE DECLARA QUE EL PLANO ES UN PRODUCT (ESTO SE HACE HACIENDO LA VARIABLE BOOL_Encontro FALSA).
        If BOOL_Encontro = False Then
            BOOL_Encontro = True
        ElseIf BOOL_Encontro = True Then
            BOOL_Encontro = False
        End If
    End If
    
    'SI BOOL_Econtro ES TRUE, EL PLANO PERTENECE A UNA PARTE, POR LO QUE SE CREA UNA CARPETA DENTRO DEL PRODUCTO. SI ES FALSE LA CARPETA SE CREA EN LA RAIZ DE PDT.
    '==============================================================================================================================================================
    If BOOL_Encontro = True Then

        BOOL_BORRAR = False
        BOOL_ERROR = False
        STR_RUTA_PN = FileName & "\"
        STR_RUTA_PROD = N_CSI & "\"
        Call MkCarpetas(BOOL_BORRAR, PathFile, STR_RUTA_PROD, STR_RUTA_PN, REV, LOOP_N, BOOL_ERROR, RUTA_FINAL, RUTA_ULTIMO_LOOP)

        If BOOL_ERROR = True Then
            Exit Sub
        End If

    Else
        'SI LO QUE SE ESTÁ DIBUJANDO ES UN PRODUCTO
        'SE VERIFICA SI EL DIRECTORIO HA SIDO CREADO
        '===========================================
        BOOL_BORRAR = False
        BOOL_ERROR = False
        STR_RUTA_PN = FileName & "\"
        STR_RUTA_PROD = ""
        Call MkCarpetas(BOOL_BORRAR, PathFile, STR_RUTA_PROD, STR_RUTA_PN, REV, LOOP_N, BOOL_ERROR, RUTA_FINAL, RUTA_ULTIMO_LOOP)

        If BOOL_ERROR = True Then
            Exit Sub
        End If

    End If

    'SE PIDE AL USUARIO QUE INTRODUZCA LA FECHA DE LIBERACIÓN
    '=========================================================
    Do
        n_do = n_do + 1
        FECHA_LISTO = True
        Fecha = InputBox("Por favor, asigne la fecha de liberación.", "Fecha de Liberacion", Date)
        
        If StrPtr(Fecha) = 0 Then
            Call LibreriasDisponibles(2)
            Exit Sub
        End If
        
        If Len(Fecha) < 8 Then
            MsgBox "La fecha esta fuera de formato (cantidad de caracteres).", vbCritical
            FECHA_LISTO = False
        ElseIf Right(Date, 4) <> Right(Fecha, 4) Then
            MsgBox "La fecha esta fuera de formato (el ańo no corresponde al ańo en curso).", vbCritical
            FECHA_LISTO = False
        ElseIf InStr(Fecha, "/") = 0 Then
            MsgBox "La fecha esta fuera de formato (los separadores deben ser '/').", vbCritical
            FECHA_LISTO = False
        End If
        
        If n_do > 5 Then
            Call LibreriasDisponibles(2)
            Exit Sub
        End If

        Err.Clear
        On Error Resume Next
        Set strParam1 = parameters1.ITEM("Drawing\FECHA_" & REV)
        strParam1.Value = Fecha
        On Error GoTo 0
        
    Loop While FECHA_LISTO = False
    
    Dim INICIO
    Dim hoja As String
    
    INICIO = InputBox("Cuantas hojas tiene el plano?", "Cantidad de hojas", "1")
    
    If StrPtr(INICIO) = 0 Then
        Call LibreriasDisponibles(2)
        Exit Sub
    End If
    
    INICIO = CInt(INICIO)
    
        'SE GUARDAN LOS PDF DE LOS PLANOS Y LAS HOJAS DE DETALLE
        '=======================================================
        RutaPDF = RUTA_ULTIMO_LOOP & FileName & ".pdf"
        'MkDir (PathFile & FileName & "\LOOP_" & LOOP_N)
        drawingDocument1.ExportData RutaPDF, "pdf"
        
        'SE BORRAN LAS HOJAS ADICIONALES
        '===============================
        HOJAS = drawingDocument1.Sheets.Count
        Dim Hoja_Aux As String
        For i = INICIO + 1 To HOJAS
            Hoja_Aux = drawingDocument1.Sheets.ITEM(i).Name
            Hoja_Aux2 = Replace(Hoja_Aux, " ", "_")
            Hoja_Aux2 = Replace(Hoja_Aux2, ".", "_")
            hoja = RUTA_ULTIMO_LOOP & FileName & "_" & Hoja_Aux2 & ".pdf"
            If CATIA.FileSystem.FileExists(hoja) = True Then
                Kill (hoja)
            End If
        Next
    
    If REVISOR_MAIL <> "NONE" Then
        DRAWING_PN = Mid(drawingDocument1.Name, 1, InStr(1, drawingDocument1.Name, ".CATDrawing") - 1)
        
        Tareas = InputBox("Usted va a colocar en circuito de revisión el P/N:" & vbNewLine & DRAWING_PN & vbNewLine & vbNewLine & _
        "Desea enviar la tarea al primer revisor?" & vbNewLine & REVISOR_MAIL & vbNewLine & vbNewLine & "Link de Referencia:", "Enviar Tarea a primer corrector.", RUTA_ULTIMO_LOOP)
    
        If StrPtr(Tareas) = 0 Then
            MsgBox "La tarea no ha sido enviada.", vbInformation
        Else
            Call EnviarTarea(REVISOR_MAIL, DRAWING_PN, intgr_N_PN, RUTA_ULTIMO_LOOP)
        End If

    End If

End If

Call LibreriasDisponibles(2)

End Sub
Sub PPTSub(ByRef internalarr() As Variant, ByRef internalarr2() As Variant, ByRef internalarr3() As Variant, NumberCaptures, Capture_folder, PN, DESC, REV, MAT_REV, ATA_CODE)

'LATE BINDING OPTION
'==================================================
'Dim appPPT As Object
'Dim ppObj As Object
'Dim slideObj As Object
'Dim pptLayout As Object
'Dim sh As Object
'Set appPPT = CreateObject("PowerPoint.Application")
'==================================================

Call PROYECTO(PROY_CODE, PROYS, ARM_SYS)

'EARLY BINDING OPTION
'====================================
Dim appPPT As PowerPoint.Application
Dim ppObj As PowerPoint.Presentation
Dim slideObj As PowerPoint.Slide
Dim pptLayout As CustomLayout
Dim sh As PowerPoint.Shape
'====================================

Set appPPT = New PowerPoint.Application
'appPPT.Visible = False
'appPPT.Presentations.Add.PageSetup.SlideOrientation = msoOrientationHorizontal
'appPPT.Presentations.Add.PageSetup.SlideSize = ppSlideSizeA3Paper
Set ppObj = appPPT.Presentations.Add
ppObj.PageSetup.SlideSize = 3

Call Rutas("LOGO", RUTA_SALIDA, PROY_CODE)

rutalogo = RUTA_SALIDA

'SE DEBEN ESTABLECER LAS ITERACIONES PARA LLENAR LOS CAMPOS DE REVISIÓN

REV_count = Asc(REV) - 64

'MsgBox MAT_REV(1, 1) & " " & MAT_REV(1, 2) & " " & MAT_REV(1, 3)

ESC = 1.5
X_AUX = -4
Y_AUX = -2

    If ESC = 1 Then
        X_AUX = 0
        Y_AUX = 0
    End If

IMI = "00"

Margenes = 10 * ESC
MargenImagen = 10 * ESC

'ROTULO DE PAGINA 1
X1 = 20.5 * ESC
X2 = 37.5 * ESC
X3 = 94 * ESC
X4 = 112.5 * ESC
X5 = 130.5 * ESC
X6 = 182.5 * ESC
X7 = 213 * ESC
X8 = 229 * ESC
X9 = 237 * ESC
XF = 245 * ESC

Y1 = 5 * ESC
Y2 = 10 * ESC
Y3 = 10.5 * ESC
Y4 = 15 * ESC
Y5 = 15.5 * ESC
Y6 = 20 * ESC
Y7 = 25 * ESC
Y8 = 27.5 * ESC
Y85 = 30 * ESC
Y9 = 33 * ESC
Y10 = 35 * ESC
Y11 = 36 * ESC
Y12 = 40 * ESC
Y13 = 40.166 * ESC
Y14 = 44.333 * ESC
Y15 = 45 * ESC
Y16 = 46 * ESC
Y17 = 48.5 * ESC
Y18 = 50 * ESC
Y19 = 52.666 * ESC
Y20 = 55 * ESC
Y21 = 56 * ESC
Y22 = 56.833 * ESC
Y23 = 60 * ESC
Y24 = 61 * ESC
YF = 66 * ESC


'ROTULO DE PAGINAS n
X1n = 21 * ESC
X2n = 39 * ESC
X3n = 131 * ESC
XFn = 195 * ESC

Y1n = 10 * ESC
Y2n = 15 * ESC
YFn = 30 * ESC

'RECTANGULO PAGINA FINAL
X1_NOTA1 = 0 * ESC
X2_NOTA1 = 220 * ESC

Y1_NOTA1 = 40 * ESC
Y2_NOTA1 = 50 * ESC

For i = 1 To NumberCaptures

    NH = NH + 1
    
    Set pptLayout = ppObj.Designs(1).SlideMaster.CustomLayouts(7)
    Set slideObj = ppObj.Slides.AddSlide(i, pptLayout)
    
    'ActivePresentation.PageSetup.SlideSize = ppSlideSizeA4Paper

    strname = internalarr(i)
    
    Set sh = slideObj.Shapes.AddPicture(strname, False, True, Margenes + MargenImagen, Margenes + MargenImagen, -1, -1)
    
    AnchoImagen = ppObj.PageSetup.SlideWidth - 2 * (Margenes + MargenImagen)
    sh.Width = AnchoImagen
                 
    '=====
    'MARCO
    '=====
    With slideObj.Shapes.AddLine(Margenes, Margenes, Margenes, ppObj.PageSetup.SlideHeight - Margenes).Line
        '.DashStyle = msoLineDashDotDot
        .ForeColor.RGB = RGB(0, 0, 0)
    End With
    With slideObj.Shapes.AddLine(ppObj.PageSetup.SlideWidth - Margenes, Margenes, ppObj.PageSetup.SlideWidth - Margenes, ppObj.PageSetup.SlideHeight - Margenes).Line
        '.DashStyle = msoLineDashDotDot
        .ForeColor.RGB = RGB(0, 0, 0)
    End With
    With slideObj.Shapes.AddLine(Margenes, Margenes, ppObj.PageSetup.SlideWidth - Margenes, Margenes).Line
        '.DashStyle = msoLineDashDotDot
        .ForeColor.RGB = RGB(0, 0, 0)
    End With
    With slideObj.Shapes.AddLine(Margenes, ppObj.PageSetup.SlideHeight - Margenes, ppObj.PageSetup.SlideWidth - Margenes, ppObj.PageSetup.SlideHeight - Margenes).Line
        '.DashStyle = msoLineDashDotDot
        .ForeColor.RGB = RGB(0, 0, 0)
    End With
    
    
    If i = 1 Then
    
        YH = -0.5 * ESC
        XH = -1.5 * ESC
        Set Logo = slideObj.Shapes.AddPicture(rutalogo, False, True, ppObj.PageSetup.SlideWidth - Margenes - X6 - XH, ppObj.PageSetup.SlideHeight - Margenes - YF - YH, -1, -1)
           
        Logo.Width = X6 - X4 + 2 * XH
        '========
        'ROTULO 1
        '========
        
        'VERTICALES
        '==========
        With slideObj.Shapes.AddLine(ppObj.PageSetup.SlideWidth - Margenes - X1, ppObj.PageSetup.SlideHeight - Margenes, ppObj.PageSetup.SlideWidth - Margenes - X1, ppObj.PageSetup.SlideHeight - Margenes - YF).Line
            '.DashStyle = msoLineDashDotDot
            .ForeColor.RGB = RGB(0, 0, 0)
        End With
        With slideObj.Shapes.AddLine(ppObj.PageSetup.SlideWidth - Margenes - X2, ppObj.PageSetup.SlideHeight - Margenes - Y11, ppObj.PageSetup.SlideWidth - Margenes - X2, ppObj.PageSetup.SlideHeight - Margenes - YF).Line
            '.DashStyle = msoLineDashDotDot
            .ForeColor.RGB = RGB(0, 0, 0)
        End With
        With slideObj.Shapes.AddLine(ppObj.PageSetup.SlideWidth - Margenes - X3, ppObj.PageSetup.SlideHeight - Margenes - Y11, ppObj.PageSetup.SlideWidth - Margenes - X3, ppObj.PageSetup.SlideHeight - Margenes - YF).Line
            '.DashStyle = msoLineDashDotDot
            .ForeColor.RGB = RGB(0, 0, 0)
        End With
        With slideObj.Shapes.AddLine(ppObj.PageSetup.SlideWidth - Margenes - X4, ppObj.PageSetup.SlideHeight - Margenes, ppObj.PageSetup.SlideWidth - Margenes - X4, ppObj.PageSetup.SlideHeight - Margenes - YF).Line
            '.DashStyle = msoLineDashDotDot
            .ForeColor.RGB = RGB(0, 0, 0)
        End With
        With slideObj.Shapes.AddLine(ppObj.PageSetup.SlideWidth - Margenes - X5, ppObj.PageSetup.SlideHeight - Margenes, ppObj.PageSetup.SlideWidth - Margenes - X5, ppObj.PageSetup.SlideHeight - Margenes - Y3).Line
            '.DashStyle = msoLineDashDotDot
            .ForeColor.RGB = RGB(0, 0, 0)
        End With
        With slideObj.Shapes.AddLine(ppObj.PageSetup.SlideWidth - Margenes - X6, ppObj.PageSetup.SlideHeight - Margenes, ppObj.PageSetup.SlideWidth - Margenes - X6, ppObj.PageSetup.SlideHeight - Margenes - YF).Line
            '.DashStyle = msoLineDashDotDot
            .ForeColor.RGB = RGB(0, 0, 0)
        End With
        With slideObj.Shapes.AddLine(ppObj.PageSetup.SlideWidth - Margenes - X7, ppObj.PageSetup.SlideHeight - Margenes, ppObj.PageSetup.SlideWidth - Margenes - X7, ppObj.PageSetup.SlideHeight - Margenes - Y23).Line
            '.DashStyle = msoLineDashDotDot
            .ForeColor.RGB = RGB(0, 0, 0)
        End With
        With slideObj.Shapes.AddLine(ppObj.PageSetup.SlideWidth - Margenes - X8, ppObj.PageSetup.SlideHeight - Margenes, ppObj.PageSetup.SlideWidth - Margenes - X8, ppObj.PageSetup.SlideHeight - Margenes - Y23).Line
            '.DashStyle = msoLineDashDotDot
            .ForeColor.RGB = RGB(0, 0, 0)
        End With
        With slideObj.Shapes.AddLine(ppObj.PageSetup.SlideWidth - Margenes - X9, ppObj.PageSetup.SlideHeight - Margenes, ppObj.PageSetup.SlideWidth - Margenes - X9, ppObj.PageSetup.SlideHeight - Margenes - Y23).Line
            '.DashStyle = msoLineDashDotDot
            .ForeColor.RGB = RGB(0, 0, 0)
        End With
        With slideObj.Shapes.AddLine(ppObj.PageSetup.SlideWidth - Margenes - XF, ppObj.PageSetup.SlideHeight - Margenes, ppObj.PageSetup.SlideWidth - Margenes - XF, ppObj.PageSetup.SlideHeight - Margenes - YF).Line
            '.DashStyle = msoLineDashDotDot
            .ForeColor.RGB = RGB(0, 0, 0)
        End With
               
        'HORIZONTALES
        '============
        'CAMPO DE MODIFICACIONES
        '=======================
        With slideObj.Shapes.AddLine(ppObj.PageSetup.SlideWidth - Margenes - X6, ppObj.PageSetup.SlideHeight - Margenes - Y1, ppObj.PageSetup.SlideWidth - Margenes - XF, ppObj.PageSetup.SlideHeight - Margenes - Y1).Line
            '.DashStyle = msoLineDashDotDot
            .ForeColor.RGB = RGB(0, 0, 0)
        End With
        With slideObj.Shapes.AddLine(ppObj.PageSetup.SlideWidth - Margenes - X6, ppObj.PageSetup.SlideHeight - Margenes - Y2, ppObj.PageSetup.SlideWidth - Margenes - XF, ppObj.PageSetup.SlideHeight - Margenes - Y2).Line
            '.DashStyle = msoLineDashDotDot
            .ForeColor.RGB = RGB(0, 0, 0)
        End With
        With slideObj.Shapes.AddLine(ppObj.PageSetup.SlideWidth - Margenes - X6, ppObj.PageSetup.SlideHeight - Margenes - Y4, ppObj.PageSetup.SlideWidth - Margenes - XF, ppObj.PageSetup.SlideHeight - Margenes - Y4).Line
            '.DashStyle = msoLineDashDotDot
            .ForeColor.RGB = RGB(0, 0, 0)
        End With
        With slideObj.Shapes.AddLine(ppObj.PageSetup.SlideWidth - Margenes - X6, ppObj.PageSetup.SlideHeight - Margenes - Y6, ppObj.PageSetup.SlideWidth - Margenes - XF, ppObj.PageSetup.SlideHeight - Margenes - Y6).Line
            '.DashStyle = msoLineDashDotDot
            .ForeColor.RGB = RGB(0, 0, 0)
        End With
        With slideObj.Shapes.AddLine(ppObj.PageSetup.SlideWidth - Margenes - X6, ppObj.PageSetup.SlideHeight - Margenes - Y7, ppObj.PageSetup.SlideWidth - Margenes - XF, ppObj.PageSetup.SlideHeight - Margenes - Y7).Line
            '.DashStyle = msoLineDashDotDot
            .ForeColor.RGB = RGB(0, 0, 0)
        End With
        With slideObj.Shapes.AddLine(ppObj.PageSetup.SlideWidth - Margenes - X6, ppObj.PageSetup.SlideHeight - Margenes - Y85, ppObj.PageSetup.SlideWidth - Margenes - XF, ppObj.PageSetup.SlideHeight - Margenes - Y85).Line
            '.DashStyle = msoLineDashDotDot
            .ForeColor.RGB = RGB(0, 0, 0)
        End With
        With slideObj.Shapes.AddLine(ppObj.PageSetup.SlideWidth - Margenes - X6, ppObj.PageSetup.SlideHeight - Margenes - Y10, ppObj.PageSetup.SlideWidth - Margenes - XF, ppObj.PageSetup.SlideHeight - Margenes - Y10).Line
            '.DashStyle = msoLineDashDotDot
            .ForeColor.RGB = RGB(0, 0, 0)
        End With
        With slideObj.Shapes.AddLine(ppObj.PageSetup.SlideWidth - Margenes - X6, ppObj.PageSetup.SlideHeight - Margenes - Y12, ppObj.PageSetup.SlideWidth - Margenes - XF, ppObj.PageSetup.SlideHeight - Margenes - Y12).Line
            '.DashStyle = msoLineDashDotDot
            .ForeColor.RGB = RGB(0, 0, 0)
        End With
        With slideObj.Shapes.AddLine(ppObj.PageSetup.SlideWidth - Margenes - X6, ppObj.PageSetup.SlideHeight - Margenes - Y15, ppObj.PageSetup.SlideWidth - Margenes - XF, ppObj.PageSetup.SlideHeight - Margenes - Y15).Line
            '.DashStyle = msoLineDashDotDot
            .ForeColor.RGB = RGB(0, 0, 0)
        End With
        With slideObj.Shapes.AddLine(ppObj.PageSetup.SlideWidth - Margenes - X6, ppObj.PageSetup.SlideHeight - Margenes - Y18, ppObj.PageSetup.SlideWidth - Margenes - XF, ppObj.PageSetup.SlideHeight - Margenes - Y18).Line
            '.DashStyle = msoLineDashDotDot
            .ForeColor.RGB = RGB(0, 0, 0)
        End With
        With slideObj.Shapes.AddLine(ppObj.PageSetup.SlideWidth - Margenes - X6, ppObj.PageSetup.SlideHeight - Margenes - Y20, ppObj.PageSetup.SlideWidth - Margenes - XF, ppObj.PageSetup.SlideHeight - Margenes - Y20).Line
            '.DashStyle = msoLineDashDotDot
            .ForeColor.RGB = RGB(0, 0, 0)
        End With
        With slideObj.Shapes.AddLine(ppObj.PageSetup.SlideWidth - Margenes - X6, ppObj.PageSetup.SlideHeight - Margenes - Y23, ppObj.PageSetup.SlideWidth - Margenes - XF, ppObj.PageSetup.SlideHeight - Margenes - Y23).Line
            '.DashStyle = msoLineDashDotDot
            .ForeColor.RGB = RGB(0, 0, 0)
        End With
        
        'LINEA DE CIERRE
        '===============
        With slideObj.Shapes.AddLine(ppObj.PageSetup.SlideWidth - Margenes, ppObj.PageSetup.SlideHeight - Margenes - YF, ppObj.PageSetup.SlideWidth - Margenes - XF, ppObj.PageSetup.SlideHeight - Margenes - YF).Line
            '.DashStyle = msoLineDashDotDot
            .ForeColor.RGB = RGB(0, 0, 0)
        End With
        
        'CAMPOS DERECHOS (ESCALA, RUGOSIDAD, TOLERANCIAS, FORMATO, HOJAS)
        '===================================================================
        With slideObj.Shapes.AddLine(ppObj.PageSetup.SlideWidth - Margenes, ppObj.PageSetup.SlideHeight - Margenes - Y5, ppObj.PageSetup.SlideWidth - Margenes - X1, ppObj.PageSetup.SlideHeight - Margenes - Y5).Line
            '.DashStyle = msoLineDashDotDot
            .ForeColor.RGB = RGB(0, 0, 0)
        End With
        With slideObj.Shapes.AddLine(ppObj.PageSetup.SlideWidth - Margenes, ppObj.PageSetup.SlideHeight - Margenes - Y8, ppObj.PageSetup.SlideWidth - Margenes - X1, ppObj.PageSetup.SlideHeight - Margenes - Y8).Line
            '.DashStyle = msoLineDashDotDot
            .ForeColor.RGB = RGB(0, 0, 0)
        End With
        With slideObj.Shapes.AddLine(ppObj.PageSetup.SlideWidth - Margenes, ppObj.PageSetup.SlideHeight - Margenes - Y11, ppObj.PageSetup.SlideWidth - Margenes - X4, ppObj.PageSetup.SlideHeight - Margenes - Y11).Line
            '.DashStyle = msoLineDashDotDot
            .ForeColor.RGB = RGB(0, 0, 0)
        End With
        With slideObj.Shapes.AddLine(ppObj.PageSetup.SlideWidth - Margenes, ppObj.PageSetup.SlideHeight - Margenes - Y16, ppObj.PageSetup.SlideWidth - Margenes - X2, ppObj.PageSetup.SlideHeight - Margenes - Y16).Line
            '.DashStyle = msoLineDashDotDot
            .ForeColor.RGB = RGB(0, 0, 0)
        End With
        With slideObj.Shapes.AddLine(ppObj.PageSetup.SlideWidth - Margenes, ppObj.PageSetup.SlideHeight - Margenes - Y21, ppObj.PageSetup.SlideWidth - Margenes - X2, ppObj.PageSetup.SlideHeight - Margenes - Y21).Line
            '.DashStyle = msoLineDashDotDot
            .ForeColor.RGB = RGB(0, 0, 0)
        End With
        
        'CAMPOS CENTRALES
        '================
        With slideObj.Shapes.AddLine(ppObj.PageSetup.SlideWidth - Margenes - X1, ppObj.PageSetup.SlideHeight - Margenes - Y3, ppObj.PageSetup.SlideWidth - Margenes - X6, ppObj.PageSetup.SlideHeight - Margenes - Y3).Line
            '.DashStyle = msoLineDashDotDot
            .ForeColor.RGB = RGB(0, 0, 0)
        End With
        With slideObj.Shapes.AddLine(ppObj.PageSetup.SlideWidth - Margenes - X4, ppObj.PageSetup.SlideHeight - Margenes - Y6, ppObj.PageSetup.SlideWidth - Margenes - X6, ppObj.PageSetup.SlideHeight - Margenes - Y6).Line
            '.DashStyle = msoLineDashDotDot
            .ForeColor.RGB = RGB(0, 0, 0)
        End With
        With slideObj.Shapes.AddLine(ppObj.PageSetup.SlideWidth - Margenes - X4, ppObj.PageSetup.SlideHeight - Margenes - Y9, ppObj.PageSetup.SlideWidth - Margenes - X6, ppObj.PageSetup.SlideHeight - Margenes - Y9).Line
            '.DashStyle = msoLineDashDotDot
            .ForeColor.RGB = RGB(0, 0, 0)
        End With
        
        'RESPONSABLES
        '============
        With slideObj.Shapes.AddLine(ppObj.PageSetup.SlideWidth - Margenes - X2, ppObj.PageSetup.SlideHeight - Margenes - Y13, ppObj.PageSetup.SlideWidth - Margenes - X4, ppObj.PageSetup.SlideHeight - Margenes - Y13).Line
            '.DashStyle = msoLineDashDotDot
            .ForeColor.RGB = RGB(0, 0, 0)
        End With
        With slideObj.Shapes.AddLine(ppObj.PageSetup.SlideWidth - Margenes - X2, ppObj.PageSetup.SlideHeight - Margenes - Y14, ppObj.PageSetup.SlideWidth - Margenes - X4, ppObj.PageSetup.SlideHeight - Margenes - Y14).Line
            '.DashStyle = msoLineDashDotDot
            .ForeColor.RGB = RGB(0, 0, 0)
        End With
        With slideObj.Shapes.AddLine(ppObj.PageSetup.SlideWidth - Margenes - X2, ppObj.PageSetup.SlideHeight - Margenes - Y17, ppObj.PageSetup.SlideWidth - Margenes - X4, ppObj.PageSetup.SlideHeight - Margenes - Y17).Line
            '.DashStyle = msoLineDashDotDot
            .ForeColor.RGB = RGB(0, 0, 0)
        End With
        With slideObj.Shapes.AddLine(ppObj.PageSetup.SlideWidth - Margenes - X2, ppObj.PageSetup.SlideHeight - Margenes - Y19, ppObj.PageSetup.SlideWidth - Margenes - X4, ppObj.PageSetup.SlideHeight - Margenes - Y19).Line
            '.DashStyle = msoLineDashDotDot
            .ForeColor.RGB = RGB(0, 0, 0)
        End With
        With slideObj.Shapes.AddLine(ppObj.PageSetup.SlideWidth - Margenes - X2, ppObj.PageSetup.SlideHeight - Margenes - Y22, ppObj.PageSetup.SlideWidth - Margenes - X4, ppObj.PageSetup.SlideHeight - Margenes - Y22).Line
            '.DashStyle = msoLineDashDotDot
            .ForeColor.RGB = RGB(0, 0, 0)
        End With
        With slideObj.Shapes.AddLine(ppObj.PageSetup.SlideWidth - Margenes - X2, ppObj.PageSetup.SlideHeight - Margenes - Y24, ppObj.PageSetup.SlideWidth - Margenes - X4, ppObj.PageSetup.SlideHeight - Margenes - Y24).Line
            '.DashStyle = msoLineDashDotDot
            .ForeColor.RGB = RGB(0, 0, 0)
        End With
        
        'HOJA
        '====
        XH = 3 * ESC + X_AUX
        YH = 2 * ESC + Y_AUX
        With slideObj.Shapes.AddTextbox(1, ppObj.PageSetup.SlideWidth - Margenes - X1 - XH, ppObj.PageSetup.SlideHeight - Margenes - Y5 - YH, 30 * ESC, 8 * ESC).TextFrame.TextRange
            .Text = "HOJA / DE"
            .Font.Size = 3 * ESC
            .Font.Name = "Arial Narrow"
        End With
        
        XH = 4.5 * ESC + X_AUX
        YH = -1.5 * ESC + Y_AUX
        HOJAS = NH & "/" & NumberCaptures
        With slideObj.Shapes.AddTextbox(1, ppObj.PageSetup.SlideWidth - Margenes - X1n - XH, ppObj.PageSetup.SlideHeight - Margenes - Y2n - YH, 25 * ESC, 8 * ESC).TextFrame.TextRange
            .ParagraphFormat.Alignment = 2
            .Text = HOJAS
            .Font.Size = 7 * ESC
            .Font.Name = "Arial Narrow"
        End With
        
        'FORMATO
        '=======
        XH = 3 * ESC + X_AUX
        YH = 3 * ESC + Y_AUX
        With slideObj.Shapes.AddTextbox(1, ppObj.PageSetup.SlideWidth - Margenes - X1 - XH, ppObj.PageSetup.SlideHeight - Margenes - Y8 - YH, 30 * ESC, 8 * ESC).TextFrame.TextRange
            .Text = "FORMATO"
            .Font.Size = 3 * ESC
            .Font.Name = "Arial Narrow"
        End With
        
        XH = 1.5 * ESC + X_AUX
        YH = 1 * ESC + Y_AUX
        With slideObj.Shapes.AddTextbox(1, ppObj.PageSetup.SlideWidth - Margenes - X1 - XH, ppObj.PageSetup.SlideHeight - Margenes - Y8 - YH, 30 * ESC, 8 * ESC).TextFrame.TextRange
            .Text = "A4"
            .Font.Size = 8 * ESC
            .Font.Name = "Arial Narrow"
        End With
        
        'RESPONSABLES
        '============
        XH = 6 * ESC + X_AUX
        YH = 3.5 * ESC + Y_AUX
        With slideObj.Shapes.AddTextbox(1, ppObj.PageSetup.SlideWidth - Margenes - X4 - XH, ppObj.PageSetup.SlideHeight - Margenes - Y13 - YH, 30 * ESC, 8 * ESC).TextFrame.TextRange
            .Text = "Aprobó"
            .Font.Size = 3 * ESC
            .Font.Name = "Arial Narrow"
        End With
        With slideObj.Shapes.AddTextbox(1, ppObj.PageSetup.SlideWidth - Margenes - X4 - XH, ppObj.PageSetup.SlideHeight - Margenes - Y14 - YH, 30 * ESC, 8 * ESC).TextFrame.TextRange
            .Text = "Ver. Resist."
            .Font.Size = 3 * ESC
            .Font.Name = "Arial Narrow"
        End With
        With slideObj.Shapes.AddTextbox(1, ppObj.PageSetup.SlideWidth - Margenes - X4 - XH, ppObj.PageSetup.SlideHeight - Margenes - Y17 - YH, 30 * ESC, 8 * ESC).TextFrame.TextRange
            .Text = "Ing. Sistemas"
            .Font.Size = 3 * ESC
            .Font.Name = "Arial Narrow"
        End With
        With slideObj.Shapes.AddTextbox(1, ppObj.PageSetup.SlideWidth - Margenes - X4 - XH, ppObj.PageSetup.SlideHeight - Margenes - Y19 - YH, 30 * ESC, 8 * ESC).TextFrame.TextRange
            .Text = "Revisó"
            .Font.Size = 3 * ESC
            .Font.Name = "Arial Narrow"
        End With
        With slideObj.Shapes.AddTextbox(1, ppObj.PageSetup.SlideWidth - Margenes - X4 - XH, ppObj.PageSetup.SlideHeight - Margenes - Y22 - YH, 30 * ESC, 8 * ESC).TextFrame.TextRange
            .Text = "Ing. Fabric."
            .Font.Size = 3 * ESC
            .Font.Name = "Arial Narrow"
        End With
        With slideObj.Shapes.AddTextbox(1, ppObj.PageSetup.SlideWidth - Margenes - X4 - XH, ppObj.PageSetup.SlideHeight - Margenes - Y24 - YH, 30 * ESC, 8 * ESC).TextFrame.TextRange
            .Text = "Diseńó"
            .Font.Size = 3 * ESC
            .Font.Name = "Arial Narrow"
        End With
        XH = 5.5 * ESC + X_AUX
        YH = 2.5 * ESC + Y_AUX
        With slideObj.Shapes.AddTextbox(1, ppObj.PageSetup.SlideWidth - Margenes - X4 - XH, ppObj.PageSetup.SlideHeight - Margenes - YF - YH, 30 * ESC, 8 * ESC).TextFrame.TextRange
            .Text = "RESPONSABLE"
            .Font.Size = 2.5 * ESC
            .Font.Name = "Arial Narrow"
        End With
        XH = -15 * ESC + X_AUX
        With slideObj.Shapes.AddTextbox(1, ppObj.PageSetup.SlideWidth - Margenes - X3 - XH, ppObj.PageSetup.SlideHeight - Margenes - YF - YH, 60 * ESC, 8 * ESC).TextFrame.TextRange
            .Text = "ID USUARIO"
            .Font.Size = 2.5 * ESC
            .Font.Name = "Arial Narrow"
        End With
            
        'USUARIOS RESPONSABLES
        '=====================
        XH = 6 * ESC + X_AUX
        YH = 3.5 * ESC + Y_AUX
        With slideObj.Shapes.AddTextbox(1, ppObj.PageSetup.SlideWidth - Margenes - X3 - XH, ppObj.PageSetup.SlideHeight - Margenes - Y13 - YH, 30 * ESC, 8 * ESC).TextFrame.TextRange
            .Text = UCase(internalarr3(5))
            .Font.Size = 3 * ESC
            .Font.Name = "Arial Narrow"
        End With
        With slideObj.Shapes.AddTextbox(1, ppObj.PageSetup.SlideWidth - Margenes - X3 - XH, ppObj.PageSetup.SlideHeight - Margenes - Y14 - YH, 30 * ESC, 8 * ESC).TextFrame.TextRange
            .Text = UCase(internalarr3(4))
            .Font.Size = 3 * ESC
            .Font.Name = "Arial Narrow"
        End With
        With slideObj.Shapes.AddTextbox(1, ppObj.PageSetup.SlideWidth - Margenes - X3 - XH, ppObj.PageSetup.SlideHeight - Margenes - Y17 - YH, 30 * ESC, 8 * ESC).TextFrame.TextRange
            .Text = UCase(internalarr3(3))
            .Font.Size = 3 * ESC
            .Font.Name = "Arial Narrow"
        End With
        With slideObj.Shapes.AddTextbox(1, ppObj.PageSetup.SlideWidth - Margenes - X3 - XH, ppObj.PageSetup.SlideHeight - Margenes - Y19 - YH, 30 * ESC, 8 * ESC).TextFrame.TextRange
            .Text = UCase(internalarr3(2))
            .Font.Size = 3 * ESC
            .Font.Name = "Arial Narrow"
        End With
        With slideObj.Shapes.AddTextbox(1, ppObj.PageSetup.SlideWidth - Margenes - X3 - XH, ppObj.PageSetup.SlideHeight - Margenes - Y22 - YH, 30 * ESC, 8 * ESC).TextFrame.TextRange
            .Text = UCase(internalarr3(1))
            .Font.Size = 3 * ESC
            .Font.Name = "Arial Narrow"
        End With
        With slideObj.Shapes.AddTextbox(1, ppObj.PageSetup.SlideWidth - Margenes - X3 - XH, ppObj.PageSetup.SlideHeight - Margenes - Y24 - YH, 30 * ESC, 8 * ESC).TextFrame.TextRange
            .Text = UCase(internalarr3(0))
            .Font.Size = 3 * ESC
            .Font.Name = "Arial Narrow"
        End With
        
        'ESCALA, RUGOSIDAD, TOLERANCIA
        '=============================
        XH = 5.5 * ESC + X_AUX
        YH = 0 * ESC + Y_AUX
        With slideObj.Shapes.AddTextbox(1, ppObj.PageSetup.SlideWidth - Margenes - X2 - XH, ppObj.PageSetup.SlideHeight - Margenes - YF - YH, 30 * ESC, 8 * ESC).TextFrame.TextRange
            .Text = "ESCALA"
            .Font.Size = 2.5 * ESC
            .Font.Name = "Arial Narrow"
        End With
        XH = 2 * ESC + X_AUX
        YH = 3.5 * ESC + Y_AUX
        With slideObj.Shapes.AddTextbox(1, ppObj.PageSetup.SlideWidth - Margenes - X1 - XH, ppObj.PageSetup.SlideHeight - Margenes - YF - YH, 30 * ESC, 8 * ESC).TextFrame.TextRange
            .Text = "N/A"
            .Font.Size = 8 * ESC
            .Font.Name = "Arial Narrow"
        End With
        
        XH = 5.5 * ESC + X_AUX
        YH = 1.5 * ESC + Y_AUX
        With slideObj.Shapes.AddTextbox(1, ppObj.PageSetup.SlideWidth - Margenes - X2 - XH, ppObj.PageSetup.SlideHeight - Margenes - Y21 - YH, 30 * ESC, 8 * ESC).TextFrame.TextRange
            .Text = "RUGOSIDAD GENERAL"
            .Font.Size = 2.5 * ESC
            .Font.Name = "Arial Narrow"
        End With
        
        XH = 5 * ESC + X_AUX
        YH = 0.5 * ESC + Y_AUX
        With slideObj.Shapes.AddTextbox(1, ppObj.PageSetup.SlideWidth - Margenes - X1 - XH, ppObj.PageSetup.SlideHeight - Margenes - Y21 - YH, 30 * ESC, 8 * ESC).TextFrame.TextRange
            .Text = "[VER NOTAS]"
            .Font.Size = 3 * ESC
            .Font.Name = "Arial Narrow"
        End With
        
        XH = 5.5 * ESC + X_AUX
        YH = 1.5 * ESC + Y_AUX
        With slideObj.Shapes.AddTextbox(1, ppObj.PageSetup.SlideWidth - Margenes - X2 - XH, ppObj.PageSetup.SlideHeight - Margenes - Y16 - YH, 30 * ESC, 8 * ESC).TextFrame.TextRange
            .Text = "TOLERANCIA GENERAL"
            .Font.Size = 2.5 * ESC
            .Font.Name = "Arial Narrow"
        End With
        
        XH = 5 * ESC + X_AUX
        YH = 0.5 * ESC + Y_AUX
        With slideObj.Shapes.AddTextbox(1, ppObj.PageSetup.SlideWidth - Margenes - X1 - XH, ppObj.PageSetup.SlideHeight - Margenes - Y16 - YH, 30 * ESC, 8 * ESC).TextFrame.TextRange
            .Text = "[VER NOTAS]"
            .Font.Size = 3 * ESC
            .Font.Name = "Arial Narrow"
        End With
        
        XH = 5 * ESC + X_AUX
        YH = 1.5 * ESC + Y_AUX
        With slideObj.Shapes.AddTextbox(1, ppObj.PageSetup.SlideWidth - Margenes - X1 - XH, ppObj.PageSetup.SlideHeight - Margenes - Y11 - YH, 30 * ESC, 8 * ESC).TextFrame.TextRange
            .Text = "[ASME Y14.5]"
            .Font.Size = 3 * ESC
            .Font.Name = "Arial Narrow"
        End With
        
        'DESIGNACIÓN
        '===========
        XH = 6 * ESC + X_AUX
        YH = 1 * ESC + Y_AUX
        With slideObj.Shapes.AddTextbox(1, ppObj.PageSetup.SlideWidth - Margenes - X4 - XH, ppObj.PageSetup.SlideHeight - Margenes - Y11 - YH, 40 * ESC, 8 * ESC).TextFrame.TextRange
            .Text = "DESIGNACIÓN:"
            .Font.Size = 3 * ESC
            .Font.Name = "Arial Narrow"
        End With
        
        If Len(DESC) < 18 Then
            XH = 2 * ESC + X_AUX
            YH = -3 * ESC + Y_AUX
            With slideObj.Shapes.AddTextbox(1, ppObj.PageSetup.SlideWidth - Margenes - X4 - XH, ppObj.PageSetup.SlideHeight - Margenes - Y11 - YH, 90 * ESC, 8 * ESC).TextFrame.TextRange
                .ParagraphFormat.Alignment = 2
                .Text = UCase(DESC)
                .Font.Size = 8 * ESC
                .Font.Name = "Arial Narrow"
            End With
        Else
            XH = 2 * ESC + X_AUX
            YH = -3 * ESC + Y_AUX
            With slideObj.Shapes.AddTextbox(1, ppObj.PageSetup.SlideWidth - Margenes - X4 - XH, ppObj.PageSetup.SlideHeight - Margenes - Y11 - YH, 90 * ESC, 8 * ESC).TextFrame.TextRange
                .ParagraphFormat.Alignment = 2
                .Text = UCase(DESC)
                .Font.Size = 6 * ESC
                .Font.Name = "Arial Narrow"
            End With
        End If
        
        XH = 2 * ESC + X_AUX
        YH = -12 * ESC + Y_AUX
        With slideObj.Shapes.AddTextbox(1, ppObj.PageSetup.SlideWidth - Margenes - X4 - XH, ppObj.PageSetup.SlideHeight - Margenes - Y11 - YH, 90 * ESC, 8 * ESC).TextFrame.TextRange
            .ParagraphFormat.Alignment = 2
            .Text = UCase(internalarr2(i))
            .Font.Size = 6 * ESC
            .Font.Name = "Arial Narrow"
        End With

        'NUMERO DE PARTE
        '===============
        XH = 6 * ESC + X_AUX
        YH = 3.5 * ESC + Y_AUX
        With slideObj.Shapes.AddTextbox(1, ppObj.PageSetup.SlideWidth - Margenes - X4 - XH, ppObj.PageSetup.SlideHeight - Margenes - Y3 - YH, 30 * ESC, 8 * ESC).TextFrame.TextRange
            .Text = "N°"
            .Font.Size = 8 * ESC
            .Font.Name = "Arial Narrow"
        End With
        XH = -15 * ESC + X_AUX
        YH = 3.5 * ESC + Y_AUX
        With slideObj.Shapes.AddTextbox(1, ppObj.PageSetup.SlideWidth - Margenes - X4 - XH, ppObj.PageSetup.SlideHeight - Margenes - Y3 - YH, 80 * ESC, 8 * ESC).TextFrame.TextRange
            .Text = UCase(PN)
            .Font.Size = 8 * ESC
            .Font.Name = "Arial Narrow"
        End With
        
        'TIPO DE DOCUMENTO
        '=================
        XH = 2.5 * ESC + X_AUX
        With slideObj.Shapes.AddTextbox(1, ppObj.PageSetup.SlideWidth - Margenes - X5 - XH, ppObj.PageSetup.SlideHeight - Margenes - Y3 - YH, 30 * ESC, 8 * ESC).TextFrame.TextRange
            .Text = "FV"
            .Font.Size = 8 * ESC
            .Font.Name = "Arial Narrow"
        End With
        
        'CODIGO DE UTILIZACION
        '=====================
        XH = -18 * ESC + X_AUX
        With slideObj.Shapes.AddTextbox(1, ppObj.PageSetup.SlideWidth - Margenes - X6 - XH, ppObj.PageSetup.SlideHeight - Margenes - Y3 - YH, 30 * ESC, 8 * ESC).TextFrame.TextRange
            .Text = "F5"
            .Font.Size = 8 * ESC
            .Font.Name = "Arial Narrow"
        End With
        
        XH = 6 * ESC + X_AUX
        YH = 1.5 * ESC + Y_AUX
        With slideObj.Shapes.AddTextbox(1, ppObj.PageSetup.SlideWidth - Margenes - X6 - XH, ppObj.PageSetup.SlideHeight - Margenes - Y3 - YH, 30 * ESC, 8 * ESC).TextFrame.TextRange
            .Text = "CODIGO UTILIZACIÓN"
            .Font.Size = 2.5 * ESC
            .Font.Name = "Arial Narrow"
        End With
        
        'CODIGO DE SISTEMA
        '=================
        XH = 6 * ESC + X_AUX
        YH = 0.5 * ESC + Y_AUX
        With slideObj.Shapes.AddTextbox(1, ppObj.PageSetup.SlideWidth - Margenes - X6 - XH, ppObj.PageSetup.SlideHeight - Margenes - Y6 - YH, 40 * ESC, 8 * ESC).TextFrame.TextRange
            .Text = "CÓDIGO SISTEMA"
            .Font.Size = 2.5 * ESC
            .Font.Name = "Arial Narrow"
        End With
        
        XH = -18 * ESC + X_AUX
        YH = 3.8 * ESC + Y_AUX
        With slideObj.Shapes.AddTextbox(1, ppObj.PageSetup.SlideWidth - Margenes - X6 - XH, ppObj.PageSetup.SlideHeight - Margenes - Y6 - YH, 40 * ESC, 8 * ESC).TextFrame.TextRange
            .Text = ATA_CODE
            .Font.Size = 8 * ESC
            .Font.Name = "Arial Narrow"
        End With
         
        'REEMPLAZA A
        '===========
        XH = 6 * ESC + X_AUX
        YH = 1 * ESC + Y_AUX
        With slideObj.Shapes.AddTextbox(1, ppObj.PageSetup.SlideWidth - Margenes - X6 - XH, ppObj.PageSetup.SlideHeight - Margenes - Y9 - YH, 80 * ESC, 8 * ESC).TextFrame.TextRange
            .Text = "Nro.de Parte - ITEM  REP. /  REEMP."
            .Font.Size = 2.5 * ESC
            .Font.Name = "Arial Narrow"
        End With
        
        'FADEA
        '=====
        XH = 1 * ESC + X_AUX
        YH = 2 * ESC + Y_AUX
        With slideObj.Shapes.AddTextbox(1, ppObj.PageSetup.SlideWidth - Margenes - X6 - XH, ppObj.PageSetup.SlideHeight - Margenes - Y17 - YH, 100 * ESC, 8 * ESC).TextFrame.TextRange
            .Text = "Fábrica Argentina de Aviones ¨Brig. San Martin¨ S.A."
            .Font.Size = 3 * ESC
            .Font.Name = "Arial Narrow"
        End With
        
        XH = 6 * ESC + X_AUX
        YH = 2 * ESC + Y_AUX
        With slideObj.Shapes.AddTextbox(1, ppObj.PageSetup.SlideWidth - Margenes - X6 - XH, ppObj.PageSetup.SlideHeight - Margenes - Y14 - YH, 75 * ESC, 8 * ESC).TextFrame.TextRange
            .Text = "Este documento es propiedad de la Fábrica Argentina de Aviones ¨Brig. San Martin¨S.A. y no puede ser usado, publicado, comunicado, o reproducido sin autorizacion."
            .Font.Size = 2.5 * ESC
            .Font.Name = "Arial Narrow"
        End With
        
        'MODIFICACIONES
        '==============
        XH = -16 * ESC + X_AUX
        With slideObj.Shapes.AddTextbox(1, ppObj.PageSetup.SlideWidth - Margenes - XF - XH, ppObj.PageSetup.SlideHeight - Margenes - YF - YH, 60 * ESC, 8 * ESC).TextFrame.TextRange
            .Text = "MODIFICACIONES"
            .Font.Size = 2.5 * ESC
            .Font.Name = "Arial Narrow"
        End With
        
        XH = 6 * ESC + X_AUX
        YH = 3 * ESC + Y_AUX
        With slideObj.Shapes.AddTextbox(1, ppObj.PageSetup.SlideWidth - Margenes - XF - XH, ppObj.PageSetup.SlideHeight - Margenes - Y23 - YH, 30 * ESC, 8 * ESC).TextFrame.TextRange
            .Text = "Rev."
            .Font.Size = 3 * ESC
            .Font.Name = "Arial Narrow"
        End With
        
        XH = 5 * ESC + X_AUX
        With slideObj.Shapes.AddTextbox(1, ppObj.PageSetup.SlideWidth - Margenes - X9 - XH, ppObj.PageSetup.SlideHeight - Margenes - Y23 - YH, 30 * ESC, 8 * ESC).TextFrame.TextRange
            .Text = "IMI"
            .Font.Size = 3 * ESC
            .Font.Name = "Arial Narrow"
        End With
        
        XH = 3 * ESC + X_AUX
        With slideObj.Shapes.AddTextbox(1, ppObj.PageSetup.SlideWidth - Margenes - X8 - XH, ppObj.PageSetup.SlideHeight - Margenes - Y23 - YH, 30 * ESC, 8 * ESC).TextFrame.TextRange
            .Text = "Fecha"
            .Font.Size = 3 * ESC
            .Font.Name = "Arial Narrow"
        End With
        
        XH = 0 * ESC + X_AUX
        With slideObj.Shapes.AddTextbox(1, ppObj.PageSetup.SlideWidth - Margenes - X7 - XH, ppObj.PageSetup.SlideHeight - Margenes - Y23 - YH, 30 * ESC, 8 * ESC).TextFrame.TextRange
            .Text = "ID USUARIO"
            .Font.Size = 3 * ESC
            .Font.Name = "Arial Narrow"
        End With
        
        
        'MODIFICACIONES RELLENO
        '======================
        For j = 1 To REV_count
            
            RENGLON = (j - 1) * 7.5
            
            XH = 5 * ESC + X_AUX
            YH = 2.5 * ESC + Y_AUX - RENGLON
            With slideObj.Shapes.AddTextbox(1, ppObj.PageSetup.SlideWidth - Margenes - XF - XH, ppObj.PageSetup.SlideHeight - Margenes - Y22 - YH, 30 * ESC, 8 * ESC).TextFrame.TextRange
                .Text = UCase(Chr(j + 64))
                .Font.Size = 5 * ESC
                .Font.Name = "Arial Narrow"
            End With
            
            XH = 5.5 * ESC + X_AUX
            With slideObj.Shapes.AddTextbox(1, ppObj.PageSetup.SlideWidth - Margenes - X9 - XH, ppObj.PageSetup.SlideHeight - Margenes - Y22 - YH, 30 * ESC, 8 * ESC).TextFrame.TextRange
                .Text = UCase(MAT_REV(j, 1))
                .Font.Size = 5 * ESC
                .Font.Name = "Arial Narrow"
            End With
            
            XH = 6 * ESC + X_AUX
            YH = 1 * ESC + Y_AUX - RENGLON
            With slideObj.Shapes.AddTextbox(1, ppObj.PageSetup.SlideWidth - Margenes - X8 - XH, ppObj.PageSetup.SlideHeight - Margenes - Y22 - YH, 30 * ESC, 8 * ESC).TextFrame.TextRange
                .Text = UCase(MAT_REV(j, 2))
                .Font.Size = 3 * ESC
                .Font.Name = "Arial Narrow"
            End With
            

            XH = -1 * ESC + X_AUX
            With slideObj.Shapes.AddTextbox(1, ppObj.PageSetup.SlideWidth - Margenes - X7 - XH, ppObj.PageSetup.SlideHeight - Margenes - Y22 - YH, 30 * ESC, 8 * ESC).TextFrame.TextRange
                .Text = UCase(MAT_REV(j, 3))
                .Font.Size = 3 * ESC
                .Font.Name = "Arial Narrow"
            End With
 
        Next 'j
       
    ElseIf i = NumberCaptures Then
    
        '===========================================================
        'ROTULO FINAL CON NOTA RECORDANDO QUE TIENEN QUE USAR EL DD3
        '===========================================================
        
        'LOGO FADEA
        '==========
        YH = -0.5 * ESC
        XH = -1.5 * ESC
        Set Logo = slideObj.Shapes.AddPicture(rutalogo, False, True, ppObj.PageSetup.SlideWidth - Margenes - XFn - XH, ppObj.PageSetup.SlideHeight - Margenes - YFn - YH, -1, -1)
           
        Logo.Width = XFn - X3n + 2 * XH
        
        'VERTICALES
        '==========
        With slideObj.Shapes.AddLine(ppObj.PageSetup.SlideWidth - Margenes - X1n, ppObj.PageSetup.SlideHeight - Margenes, ppObj.PageSetup.SlideWidth - Margenes - X1n, ppObj.PageSetup.SlideHeight - Margenes - YFn).Line
            '.DashStyle = msoLineDashDotDot
            .ForeColor.RGB = RGB(0, 0, 0)
        End With
        With slideObj.Shapes.AddLine(ppObj.PageSetup.SlideWidth - Margenes - X2n, ppObj.PageSetup.SlideHeight - Margenes, ppObj.PageSetup.SlideWidth - Margenes - X2n, ppObj.PageSetup.SlideHeight - Margenes - YFn).Line
            '.DashStyle = msoLineDashDotDot
            .ForeColor.RGB = RGB(0, 0, 0)
        End With
        With slideObj.Shapes.AddLine(ppObj.PageSetup.SlideWidth - Margenes - X3n, ppObj.PageSetup.SlideHeight - Margenes, ppObj.PageSetup.SlideWidth - Margenes - X3n, ppObj.PageSetup.SlideHeight - Margenes - YFn).Line
            '.DashStyle = msoLineDashDotDot
            .ForeColor.RGB = RGB(0, 0, 0)
        End With
        With slideObj.Shapes.AddLine(ppObj.PageSetup.SlideWidth - Margenes - XFn, ppObj.PageSetup.SlideHeight - Margenes, ppObj.PageSetup.SlideWidth - Margenes - XFn, ppObj.PageSetup.SlideHeight - Margenes - YFn).Line
            '.DashStyle = msoLineDashDotDot
            .ForeColor.RGB = RGB(0, 0, 0)
        End With
'                       NOTA FINAL
'                    X1_NOTA1 = 200 * Esc
'                    X2_NOTA1 = 280 * Esc
'
'                    Y1_NOTA1 = 20 * Esc
'                    Y2_NOTA1 = 30 * Esc
        With slideObj.Shapes.AddLine(ppObj.PageSetup.SlideWidth - Margenes - X1_NOTA1, ppObj.PageSetup.SlideHeight - Margenes - Y1_NOTA1, ppObj.PageSetup.SlideWidth - Margenes - X1_NOTA1, ppObj.PageSetup.SlideHeight - Margenes - Y2_NOTA1).Line
            '.DashStyle = msoLineDashDotDot
            .ForeColor.RGB = RGB(0, 0, 0)
        End With
        With slideObj.Shapes.AddLine(ppObj.PageSetup.SlideWidth - Margenes - X2_NOTA1, ppObj.PageSetup.SlideHeight - Margenes - Y1_NOTA1, ppObj.PageSetup.SlideWidth - Margenes - X2_NOTA1, ppObj.PageSetup.SlideHeight - Margenes - Y2_NOTA1).Line
            '.DashStyle = msoLineDashDotDot
            .ForeColor.RGB = RGB(0, 0, 0)
        End With
        
        'HORIZONTALES
        '============
        With slideObj.Shapes.AddLine(ppObj.PageSetup.SlideWidth - Margenes - X2n, ppObj.PageSetup.SlideHeight - Margenes - Y1n, ppObj.PageSetup.SlideWidth - Margenes - X3n, ppObj.PageSetup.SlideHeight - Margenes - Y1n).Line
            '.DashStyle = msoLineDashDotDot
            .ForeColor.RGB = RGB(0, 0, 0)
        End With
        With slideObj.Shapes.AddLine(ppObj.PageSetup.SlideWidth - Margenes, ppObj.PageSetup.SlideHeight - Margenes - Y2n, ppObj.PageSetup.SlideWidth - Margenes - X2n, ppObj.PageSetup.SlideHeight - Margenes - Y2n).Line
            '.DashStyle = msoLineDashDotDot
            .ForeColor.RGB = RGB(0, 0, 0)
        End With
        With slideObj.Shapes.AddLine(ppObj.PageSetup.SlideWidth - Margenes, ppObj.PageSetup.SlideHeight - Margenes - YFn, ppObj.PageSetup.SlideWidth - Margenes - XFn, ppObj.PageSetup.SlideHeight - Margenes - YFn).Line
            '.DashStyle = msoLineDashDotDot
            .ForeColor.RGB = RGB(0, 0, 0)
        End With
        
        'NOTA FINAL
        With slideObj.Shapes.AddLine(ppObj.PageSetup.SlideWidth - Margenes - X1_NOTA1, ppObj.PageSetup.SlideHeight - Margenes - Y1_NOTA1, ppObj.PageSetup.SlideWidth - Margenes - X2_NOTA1, ppObj.PageSetup.SlideHeight - Margenes - Y1_NOTA1).Line
            '.DashStyle = msoLineDashDotDot
            .ForeColor.RGB = RGB(0, 0, 0)
        End With
        With slideObj.Shapes.AddLine(ppObj.PageSetup.SlideWidth - Margenes - X1_NOTA1, ppObj.PageSetup.SlideHeight - Margenes - Y2_NOTA1, ppObj.PageSetup.SlideWidth - Margenes - X2_NOTA1, ppObj.PageSetup.SlideHeight - Margenes - Y2_NOTA1).Line
            '.DashStyle = msoLineDashDotDot
            .ForeColor.RGB = RGB(0, 0, 0)
        End With
    
        'FADEA
        '=====
        XH = 4 * ESC + X_AUX
        YH = -13 * ESC + Y_AUX
        With slideObj.Shapes.AddTextbox(1, ppObj.PageSetup.SlideWidth - Margenes - XFn - XH, ppObj.PageSetup.SlideHeight - Margenes - YFn - YH, 100 * ESC, 8 * ESC).TextFrame.TextRange
            .Text = "Fábrica Argentina de Aviones ¨Brig. San Martin¨ S.A."
            .Font.Size = 3 * ESC
            .Font.Name = "Arial Narrow"
        End With
        
        XH = 6 * ESC + X_AUX
        YH = -17 * ESC + Y_AUX
        With slideObj.Shapes.AddTextbox(1, ppObj.PageSetup.SlideWidth - Margenes - XFn - XH, ppObj.PageSetup.SlideHeight - Margenes - YFn - YH, 70 * ESC, 8 * ESC).TextFrame.TextRange
            .Text = "Este documento es propiedad de la Fábrica Argentina de Aviones ¨Brig. San Martin¨S.A. y no puede ser usado, publicado, comunicado, o reproducido sin autorizacion."
            .Font.Size = 2.5 * ESC
            .Font.Name = "Arial Narrow"
        End With
    
        'DESIGNACION
        '===========
        XH = 2 * ESC + X_AUX '-3
        YH = 1 * ESC + Y_AUX
        If Len(DESC) < 18 Then
            With slideObj.Shapes.AddTextbox(1, ppObj.PageSetup.SlideWidth - Margenes - X3n - XH, ppObj.PageSetup.SlideHeight - Margenes - YFn - YH, 90 * ESC, 8 * ESC).TextFrame.TextRange
                .ParagraphFormat.Alignment = 2
                .Text = UCase(DESC)
                .Font.Size = 8 * ESC
                .Font.Name = "Arial Narrow"
            End With
        Else
            With slideObj.Shapes.AddTextbox(1, ppObj.PageSetup.SlideWidth - Margenes - X3n - XH, ppObj.PageSetup.SlideHeight - Margenes - YFn - YH, 90 * ESC, 8 * ESC).TextFrame.TextRange
                .ParagraphFormat.Alignment = 2
                .Text = UCase(DESC)
                .Font.Size = 6 * ESC
                .Font.Name = "Arial Narrow"
            End With
        End If
        
        XH = -3 * ESC + X_AUX
        YH = -7 * ESC + Y_AUX
        With slideObj.Shapes.AddTextbox(1, ppObj.PageSetup.SlideWidth - Margenes - X3n - XH, ppObj.PageSetup.SlideHeight - Margenes - YFn - YH, 80 * ESC, 8 * ESC).TextFrame.TextRange
            .ParagraphFormat.Alignment = 2
            .Text = UCase(internalarr2(i))
            .Font.Size = 6 * ESC
            .Font.Name = "Arial Narrow"
        End With
        
        'NOTA FINAL
        XH = -3 * ESC + X_AUX
        YH = -7 * ESC + Y_AUX
        With slideObj.Shapes.AddTextbox(1, ppObj.PageSetup.SlideWidth - Margenes - X2_NOTA1 - XH, ppObj.PageSetup.SlideHeight - Margenes - Y2_NOTA1 - 2, 270 * ESC, 8 * ESC).TextFrame.TextRange
            .ParagraphFormat.Alignment = 1
            .Text = "POR INFORMACIÓN GEOMÉTRICA COMPLEMENTARIA VER DD3-" & PN & "-" & REV
            .Font.Size = 6 * ESC
            .Font.Name = "Arial Narrow"
        End With
        
        
        'PN
        '==
        XH = -15 * ESC + X_AUX
        YH = 3.5 * ESC + Y_AUX
        With slideObj.Shapes.AddTextbox(1, ppObj.PageSetup.SlideWidth - Margenes - X3n - XH, ppObj.PageSetup.SlideHeight - Margenes - Y1n - YH, 80 * ESC, 8 * ESC).TextFrame.TextRange
            .Text = PN
            .Font.Size = 8 * ESC
            .Font.Name = "Arial Narrow"
        End With
        
        'ESCALA
        '======
        XH = 3 * ESC + X_AUX
        YH = 2 * ESC + Y_AUX
        With slideObj.Shapes.AddTextbox(1, ppObj.PageSetup.SlideWidth - Margenes - X2n - XH, ppObj.PageSetup.SlideHeight - Margenes - YFn - YH, 30 * ESC, 8 * ESC).TextFrame.TextRange
            .Text = "ESCALA"
            .Font.Size = 2.5 * ESC
            .Font.Name = "Arial Narrow"
        End With
        XH = 4 * ESC + X_AUX
        YH = -1 * ESC + Y_AUX
        With slideObj.Shapes.AddTextbox(1, ppObj.PageSetup.SlideWidth - Margenes - X2n - XH, ppObj.PageSetup.SlideHeight - Margenes - YFn - YH, 30 * ESC, 8 * ESC).TextFrame.TextRange
            .Text = "N/A"
            .Font.Size = 8 * ESC
            .Font.Name = "Arial Narrow"
        End With
        
        'FORMATO
        '=======
        XH = 2 * ESC + X_AUX
        YH = 2 * ESC + Y_AUX
        With slideObj.Shapes.AddTextbox(1, ppObj.PageSetup.SlideWidth - Margenes - X1n - XH, ppObj.PageSetup.SlideHeight - Margenes - YFn - YH, 30 * ESC, 8 * ESC).TextFrame.TextRange
            .Text = "FORMATO"
            .Font.Size = 2.5 * ESC
            .Font.Name = "Arial Narrow"
        End With
        XH = 1 * ESC + X_AUX
        YH = -1 * ESC + Y_AUX
        With slideObj.Shapes.AddTextbox(1, ppObj.PageSetup.SlideWidth - Margenes - X1n - XH, ppObj.PageSetup.SlideHeight - Margenes - YFn - YH, 30 * ESC, 8 * ESC).TextFrame.TextRange
            .Text = "A4"
            .Font.Size = 8 * ESC
            .Font.Name = "Arial Narrow"
        End With
        
        'REVISION
        '========
        XH = 1 * ESC + X_AUX
        YH = 2 * ESC + Y_AUX
        With slideObj.Shapes.AddTextbox(1, ppObj.PageSetup.SlideWidth - Margenes - X2n - XH, ppObj.PageSetup.SlideHeight - Margenes - Y2n - YH, 30 * ESC, 8 * ESC).TextFrame.TextRange
            .Text = "REV."
            .Font.Size = 2.5 * ESC
            .Font.Name = "Arial Narrow"
        End With
        XH = 1 * ESC + X_AUX
        YH = -1 * ESC + Y_AUX
        With slideObj.Shapes.AddTextbox(1, ppObj.PageSetup.SlideWidth - Margenes - X2n - XH, ppObj.PageSetup.SlideHeight - Margenes - Y2n - YH, 30 * ESC, 8 * ESC).TextFrame.TextRange
            .Text = REV
            .Font.Size = 8 * ESC
            .Font.Name = "Arial Narrow"
        End With
        
        'HOJA
        '====
        XH = 2 * ESC + X_AUX
        YH = 2 * ESC + Y_AUX
        With slideObj.Shapes.AddTextbox(1, ppObj.PageSetup.SlideWidth - Margenes - X1n - XH, ppObj.PageSetup.SlideHeight - Margenes - Y2n - YH, 30 * ESC, 8 * ESC).TextFrame.TextRange
            .Text = "HOJA / DE"
            .Font.Size = 2.5 * ESC
            .Font.Name = "Arial Narrow"
        End With
        
        XH = 4.5 * ESC + X_AUX
        YH = -1.5 * ESC + Y_AUX
        HOJAS = NH & "/" & NumberCaptures
        With slideObj.Shapes.AddTextbox(1, ppObj.PageSetup.SlideWidth - Margenes - X1n - XH, ppObj.PageSetup.SlideHeight - Margenes - Y2n - YH, 25 * ESC, 8 * ESC).TextFrame.TextRange
            .ParagraphFormat.Alignment = 2
            .Text = HOJAS
            .Font.Size = 7 * ESC
            .Font.Name = "Arial Narrow"
        End With
    
    Else
    
        '========
        'ROTULO n
        '========
        'LOGO FADEA
        '==========
        YH = -0.5 * ESC
        XH = -1.5 * ESC
        Set Logo = slideObj.Shapes.AddPicture(rutalogo, False, True, ppObj.PageSetup.SlideWidth - Margenes - XFn - XH, ppObj.PageSetup.SlideHeight - Margenes - YFn - YH, -1, -1)
           
        Logo.Width = XFn - X3n + 2 * XH
        
        'VERTICALES
        '==========
        With slideObj.Shapes.AddLine(ppObj.PageSetup.SlideWidth - Margenes - X1n, ppObj.PageSetup.SlideHeight - Margenes, ppObj.PageSetup.SlideWidth - Margenes - X1n, ppObj.PageSetup.SlideHeight - Margenes - YFn).Line
            '.DashStyle = msoLineDashDotDot
            .ForeColor.RGB = RGB(0, 0, 0)
        End With
        With slideObj.Shapes.AddLine(ppObj.PageSetup.SlideWidth - Margenes - X2n, ppObj.PageSetup.SlideHeight - Margenes, ppObj.PageSetup.SlideWidth - Margenes - X2n, ppObj.PageSetup.SlideHeight - Margenes - YFn).Line
            '.DashStyle = msoLineDashDotDot
            .ForeColor.RGB = RGB(0, 0, 0)
        End With
        With slideObj.Shapes.AddLine(ppObj.PageSetup.SlideWidth - Margenes - X3n, ppObj.PageSetup.SlideHeight - Margenes, ppObj.PageSetup.SlideWidth - Margenes - X3n, ppObj.PageSetup.SlideHeight - Margenes - YFn).Line
            '.DashStyle = msoLineDashDotDot
            .ForeColor.RGB = RGB(0, 0, 0)
        End With
        With slideObj.Shapes.AddLine(ppObj.PageSetup.SlideWidth - Margenes - XFn, ppObj.PageSetup.SlideHeight - Margenes, ppObj.PageSetup.SlideWidth - Margenes - XFn, ppObj.PageSetup.SlideHeight - Margenes - YFn).Line
            '.DashStyle = msoLineDashDotDot
            .ForeColor.RGB = RGB(0, 0, 0)
        End With
        
        'HORIZONTALES
        '============
        With slideObj.Shapes.AddLine(ppObj.PageSetup.SlideWidth - Margenes - X2n, ppObj.PageSetup.SlideHeight - Margenes - Y1n, ppObj.PageSetup.SlideWidth - Margenes - X3n, ppObj.PageSetup.SlideHeight - Margenes - Y1n).Line
            '.DashStyle = msoLineDashDotDot
            .ForeColor.RGB = RGB(0, 0, 0)
        End With
        With slideObj.Shapes.AddLine(ppObj.PageSetup.SlideWidth - Margenes, ppObj.PageSetup.SlideHeight - Margenes - Y2n, ppObj.PageSetup.SlideWidth - Margenes - X2n, ppObj.PageSetup.SlideHeight - Margenes - Y2n).Line
            '.DashStyle = msoLineDashDotDot
            .ForeColor.RGB = RGB(0, 0, 0)
        End With
        With slideObj.Shapes.AddLine(ppObj.PageSetup.SlideWidth - Margenes, ppObj.PageSetup.SlideHeight - Margenes - YFn, ppObj.PageSetup.SlideWidth - Margenes - XFn, ppObj.PageSetup.SlideHeight - Margenes - YFn).Line
            '.DashStyle = msoLineDashDotDot
            .ForeColor.RGB = RGB(0, 0, 0)
        End With
    
        'FADEA
        '=====
        XH = 4 * ESC + X_AUX
        YH = -13 * ESC + Y_AUX
        With slideObj.Shapes.AddTextbox(1, ppObj.PageSetup.SlideWidth - Margenes - XFn - XH, ppObj.PageSetup.SlideHeight - Margenes - YFn - YH, 100 * ESC, 8 * ESC).TextFrame.TextRange
            .Text = "Fábrica Argentina de Aviones ¨Brig. San Martin¨ S.A."
            .Font.Size = 3 * ESC
            .Font.Name = "Arial Narrow"
        End With
        
        XH = 6 * ESC + X_AUX
        YH = -17 * ESC + Y_AUX
        With slideObj.Shapes.AddTextbox(1, ppObj.PageSetup.SlideWidth - Margenes - XFn - XH, ppObj.PageSetup.SlideHeight - Margenes - YFn - YH, 70 * ESC, 8 * ESC).TextFrame.TextRange
            .Text = "Este documento es propiedad de la Fábrica Argentina de Aviones ¨Brig. San Martin¨S.A. y no puede ser usado, publicado, comunicado, o reproducido sin autorizacion."
            .Font.Size = 2.5 * ESC
            .Font.Name = "Arial Narrow"
        End With
    
        'DESIGNACION
        '===========
        XH = 2 * ESC + X_AUX '-3
        YH = 1 * ESC + Y_AUX
        If Len(DESC) < 18 Then
            With slideObj.Shapes.AddTextbox(1, ppObj.PageSetup.SlideWidth - Margenes - X3n - XH, ppObj.PageSetup.SlideHeight - Margenes - YFn - YH, 90 * ESC, 8 * ESC).TextFrame.TextRange
                .ParagraphFormat.Alignment = 2
                .Text = UCase(DESC)
                .Font.Size = 8 * ESC
                .Font.Name = "Arial Narrow"
            End With
        Else
            With slideObj.Shapes.AddTextbox(1, ppObj.PageSetup.SlideWidth - Margenes - X3n - XH, ppObj.PageSetup.SlideHeight - Margenes - YFn - YH, 90 * ESC, 8 * ESC).TextFrame.TextRange
                .ParagraphFormat.Alignment = 2
                .Text = UCase(DESC)
                .Font.Size = 6 * ESC
                .Font.Name = "Arial Narrow"
            End With
        End If
        
        XH = -3 * ESC + X_AUX
        YH = -7 * ESC + Y_AUX
        With slideObj.Shapes.AddTextbox(1, ppObj.PageSetup.SlideWidth - Margenes - X3n - XH, ppObj.PageSetup.SlideHeight - Margenes - YFn - YH, 80 * ESC, 8 * ESC).TextFrame.TextRange
            .ParagraphFormat.Alignment = 2
            .Text = UCase(internalarr2(i))
            .Font.Size = 6 * ESC
            .Font.Name = "Arial Narrow"
        End With
        
        'PN
        '==
        XH = -15 * ESC + X_AUX
        YH = 3.5 * ESC + Y_AUX
        With slideObj.Shapes.AddTextbox(1, ppObj.PageSetup.SlideWidth - Margenes - X3n - XH, ppObj.PageSetup.SlideHeight - Margenes - Y1n - YH, 80 * ESC, 8 * ESC).TextFrame.TextRange
            .Text = PN
            .Font.Size = 8 * ESC
            .Font.Name = "Arial Narrow"
        End With
        
        'ESCALA
        '======
        XH = 3 * ESC + X_AUX
        YH = 2 * ESC + Y_AUX
        With slideObj.Shapes.AddTextbox(1, ppObj.PageSetup.SlideWidth - Margenes - X2n - XH, ppObj.PageSetup.SlideHeight - Margenes - YFn - YH, 30 * ESC, 8 * ESC).TextFrame.TextRange
            .Text = "ESCALA"
            .Font.Size = 2.5 * ESC
            .Font.Name = "Arial Narrow"
        End With
        XH = 4 * ESC + X_AUX
        YH = -1 * ESC + Y_AUX
        With slideObj.Shapes.AddTextbox(1, ppObj.PageSetup.SlideWidth - Margenes - X2n - XH, ppObj.PageSetup.SlideHeight - Margenes - YFn - YH, 30 * ESC, 8 * ESC).TextFrame.TextRange
            .Text = "N/A"
            .Font.Size = 8 * ESC
            .Font.Name = "Arial Narrow"
        End With
        
        'FORMATO
        '=======
        XH = 2 * ESC + X_AUX
        YH = 2 * ESC + Y_AUX
        With slideObj.Shapes.AddTextbox(1, ppObj.PageSetup.SlideWidth - Margenes - X1n - XH, ppObj.PageSetup.SlideHeight - Margenes - YFn - YH, 30 * ESC, 8 * ESC).TextFrame.TextRange
            .Text = "FORMATO"
            .Font.Size = 2.5 * ESC
            .Font.Name = "Arial Narrow"
        End With
        XH = 1 * ESC + X_AUX
        YH = -1 * ESC + Y_AUX
        With slideObj.Shapes.AddTextbox(1, ppObj.PageSetup.SlideWidth - Margenes - X1n - XH, ppObj.PageSetup.SlideHeight - Margenes - YFn - YH, 30 * ESC, 8 * ESC).TextFrame.TextRange
            .Text = "A4"
            .Font.Size = 8 * ESC
            .Font.Name = "Arial Narrow"
        End With
        
        'REVISION
        '========
        XH = 1 * ESC + X_AUX
        YH = 2 * ESC + Y_AUX
        With slideObj.Shapes.AddTextbox(1, ppObj.PageSetup.SlideWidth - Margenes - X2n - XH, ppObj.PageSetup.SlideHeight - Margenes - Y2n - YH, 30 * ESC, 8 * ESC).TextFrame.TextRange
            .Text = "REV."
            .Font.Size = 2.5 * ESC
            .Font.Name = "Arial Narrow"
        End With
        XH = 1 * ESC + X_AUX
        YH = -1 * ESC + Y_AUX
        With slideObj.Shapes.AddTextbox(1, ppObj.PageSetup.SlideWidth - Margenes - X2n - XH, ppObj.PageSetup.SlideHeight - Margenes - Y2n - YH, 30 * ESC, 8 * ESC).TextFrame.TextRange
            .Text = REV
            .Font.Size = 8 * ESC
            .Font.Name = "Arial Narrow"
        End With
        
        'HOJA
        '====
        XH = 2 * ESC + X_AUX
        YH = 2 * ESC + Y_AUX
        With slideObj.Shapes.AddTextbox(1, ppObj.PageSetup.SlideWidth - Margenes - X1n - XH, ppObj.PageSetup.SlideHeight - Margenes - Y2n - YH, 30 * ESC, 8 * ESC).TextFrame.TextRange
            .Text = "HOJA / DE"
            .Font.Size = 2.5 * ESC
            .Font.Name = "Arial Narrow"
        End With
        
        XH = 4.5 * ESC + X_AUX
        YH = -1.5 * ESC + Y_AUX
        HOJAS = NH & "/" & NumberCaptures
        With slideObj.Shapes.AddTextbox(1, ppObj.PageSetup.SlideWidth - Margenes - X1n - XH, ppObj.PageSetup.SlideHeight - Margenes - Y2n - YH, 25 * ESC, 8 * ESC).TextFrame.TextRange
            .ParagraphFormat.Alignment = 2
            .Text = HOJAS
            .Font.Size = 7 * ESC
            .Font.Name = "Arial Narrow"
        End With
 
    End If

Next

'Err
'MsgBox Err.Value
On Error Resume Next
ppObj.ExportAsFixedFormat Capture_folder & ".pdf", 2, 2, 1, 1, 1, 0, , 1, , False, False, False, False, False


'If Err.Value <> 0 Then
'MsgBox "Debe cerrar el archivo, antes "
'
'End If

For i = 1 To NumberCaptures
Kill internalarr(i)
Next
On Error GoTo 0

ppObj.Close
appPPT.Quit

End Sub

Sub EnviarTarea(REVISOR, ITEM, intgr_N_PN, RUTA_FINAL)

Dim OutlookApp As Object
Dim objTask As Object

Const olMailItem = 0
Const olAppointmentItem = 1
Const olContactItem = 2
Const olTaskItem = 3
Const olJournalItem = 4
Const olNoteItem = 5
Const olPostItem = 6
Const olPink = 2

Err.Clear
On Error Resume Next
Set OutlookApp = CreateObject("Outlook.Application")

If Err.Number <> 0 Then
    Err.Clear
    Set OutlookApp = GetObject(, "Outlook.Application")
End If

Set objTask = OutlookApp.CreateItem(olTaskItem)

With objTask
.Subject = "Revisar P/N " & Left(ITEM, intgr_N_PN)
.startdate = Now()
.DueDate = Now() + 1
.Body = "<" & RUTA_FINAL & ITEM & ">"
.Save
End With


    objTask.Recipients.Add (REVISOR)

    With objTask
    .Recipients.ResolveAll
    .Assign
    .Send
    End With

On Error GoTo 0

'If Err.Value <> 0 Then
'MsgBox "Para enviar la tarea debe tener abierto (minimizado) Outlook." & vbNewLine & vbNewLine & "Ábralo e intente nuevamente.", vbCritical
'End If

End Sub

Public Function ParameterExist(ByRef ParameterCollection As Parameters, ByVal ParameterName As String, ByRef OutputParameter As Parameter) As Boolean
    
    On Error Resume Next
    Err.Clear
    Set OutputParameter = ParameterCollection.ITEM(ParameterName)
    If Err.Number = 0 Then
        ParameterExist = True
    Else
        ParameterExist = False
    End If
    On Error GoTo 0

End Function

Sub BuscarRev(PN, REV, msgerror, TIPO_DOC)

msgerror = False
Call PROYECTO(PROY_CODE, PROYS, ARM_SYS)

Call Rutas(TIPO_DOC, RUTA_SALIDA, PROY_CODE)

For br = 1 To 10

    REV = UCase(Chr(64 + br))
    
    Err.Clear
    On Error GoTo errorDocTec
    
    If TIPO_DOC = "DD3" Then
        rutaFV = RUTA_SALIDA & TIPO_DOC & "-" & PN & "-" & REV & ".CATPart"
    ElseIf TIPO_DOC = "ZG" Then
        rutaFV = RUTA_SALIDA & TIPO_DOC & "-" & PN & "-" & REV & ".pdf"
    ElseIf TIPO_DOC = "PD3" Then
        rutaFV = RUTA_SALIDA & TIPO_DOC & "-" & PN & "-" & REV & ".pdf"
    ElseIf TIPO_DOC = "FV" Then
        rutaFV = RUTA_SALIDA & TIPO_DOC & "-" & PN & "-" & REV & ".pdf"
    End If
    
    If Len(Dir(rutaFV)) = 0 Then  'si el archivo no existe se declara que esta el la revision adecuada y se sale de la subrutina
        msgerror = False
        Exit Sub
    End If

Next

errorDocTec:
MsgBox "Usted no tiene acceso a las carpetas de documentación técnica. Debe generar un requerimiento de acceso antes de generar un FV."
msgerror = True
On Error GoTo -1

End Sub

Sub CreaRotulo(ByRef internalarr3() As Variant, Ruta_ROTULO, PN, DESC, REV, MAT_REV, REV_count)

    On Error Resume Next
    Dim arr4(0 To 5) As Variant

    Call NCONTROL(internalarr3, arr4)

    Dim RotuloTXT As String
    RotuloTXT = Ruta_ROTULO & PN & "-" & REV & "_ROTULO_PD3.txt"

    Dim fso As Object
    Set fso = CreateObject("Scripting.FileSystemObject")
    Dim fileStream As Object

    Call PROYECTO(PROY_CODE, PROYS, ARM_SYS)

    Call Rutas("LOGO_PROPIEDAD", RUTA_SALIDA, PROY_CODE)

    Set fileStream = fso.CreateTextFile(RotuloTXT)
    
    'SE ESCRIBE EL RÓTULO
    fileStream.WriteLine PN & " / " & DESC
    fileStream.WriteLine "Rev: " & REV & " / IMI: " & MAT_REV(REV_count, 1) & " / Aut: " & arr4(0) & " (" & MAT_REV(REV_count, 2) & ") / VE: " & arr4(4)
    fileStream.WriteLine "VS: " & arr4(3) & " / Aprob: " & arr4(5) & " / " & ARM_SYS & " / Sup: " & internalarr3(6)
    fileStream.Close
    
    'SE COPIA EL LOGO DE FADEA A LA CARPETA LOOP
    Set fso = VBA.CreateObject("Scripting.FileSystemObject")
    fso.CopyFile RUTA_SALIDA, Ruta_ROTULO
    On Error GoTo 0
    
End Sub

Sub NCONTROL(ByRef internalarr3 As Variant, internalarr4)

Call Usuarios(ARR_USUARIOS)

For p = 0 To 5
    For q = 1 To UBound(ARR_USUARIOS)
        If internalarr3(p) = ARR_USUARIOS(q, 1) Then
            internalarr4(p) = ARR_USUARIOS(q, 2)
        End If
    Next
Next

End Sub

Sub Reset_CAPTURAS(oAnnotationSets, oSel, sCapSel, AnnoSet1)

On Error Resume Next
'SE RECORRE TODO EL ARBOL DE ANOTACIONES
'=======================================
For IdxSet = 1 To oAnnotationSets.Count
    Set oAnnotationSet = oAnnotationSets.ITEM(IdxSet)
    Set oAnnotations = oAnnotationSet.Annotations
    For IdxAnnot = 1 To oAnnotations.Count

        'SE CAMBIA EL COLOR DE CADA ANOTACION
        '====================================
        Set oAnnotation = oAnnotations.ITEM(IdxAnnot)
        If Not oAnnotation Is Nothing Then
            With oSel
                .Clear
                .Add oAnnotation
                Call .VisProperties.SetVisibleColor(255, 255, 255, 0)
            End With
            oAnnotation.ModifyVisu
        End If
    Next
Next

sCapSel.Clear
sCapSel.Add AnnoSet1.Captures.ITEM(1)
On Error Resume Next
AnnoSet1.Captures.ITEM(1).DisplayCapture
On Error GoTo 0
sCapSel.Clear
On Error GoTo 0

End Sub

Attribute VB_Name = "A95_Generar_Revision_PN"
'AUTOR: SEBASTIAN ASSAIN
'NOMBRE: A95_Generar_Revision_PN
'VERSION 0.5
'FECHA: 22/09/2020
'CAMBIOS:   -
'FRASE: NO PUEDES COMETER 2 VECES EL MISMO ERROR, LA SEGUNDA VEZ SERÁ POR ELECCIÓN
'DESCRIPCIÓN: GENERA REVISIONES A APRTIR DE PN LIBERADOS VOLVIENDOLOS A LA CARPETA PROCESOS
Public PROYS() As Variant

Sub CATMain()
'CATIA.DisplayFileAlerts = False
'DrawingDocument

Dim Archivo_Existente As Variant
Dim Ruta As String
Dim RUTA_SALIDA As String
Dim Nombre_Ruta As String
Dim Nombre_Ruta_Archivo_Guardado As String
Dim Nombre_Archivo As String
Dim Nombre_Liberado As String
Dim Reemplazo As VbMsgBoxResult
Dim Armonizado As VbMsgBoxResult
Dim Tipo_Archivo As String
Dim Nom_PartProd As String
Dim producto As Product
Dim relationsproducto1 As Relations
Dim productDocument1 As ProductDocument
Dim product1 As Product
Dim partDocument1 As PartDocument
Dim part1 As Part
Dim relationsparte1 As Relations
Dim oseleccion As Selection
Dim Instancia As String
Dim Instancia_sp As String
Dim NInst As Variant
Dim NInst_Nueva As Variant
Dim retro As Integer
Dim BuscaPunto As String
Dim InstVec() As Variant
Dim NInstVec() As Variant
Dim Cambio As Boolean
Dim BodyToRename As Body
Dim strParam1 As StrParam
Dim parameters1 As Parameters
Dim Param As Parameter
Dim publications1 As Publications


'If UCase(Environ("username")) = "USUARIO" Or UCase(Environ("username")) = "TARDITTI" Or UCase(Environ("username")) = "FRETE" Or _
'UCase(Environ("username")) = "SCARCELLA" Or UCase(Environ("username")) = "CONTRERASC" Or UCase(Environ("username")) = "NUNES" Or _
'UCase(Environ("username")) = "QUELAS" Or UCase(Environ("username")) = "TOSELLI" Or UCase(Environ("username")) = "ASSAIN" Or _
'UCase(Environ("username")) = "TOLEDO" Then

'SI NO EXISTE NINGUN DOCUMENTO ABIERTO SE EVITA QUE LA MACRO DEVUELVA UN ERROR
'=============================================================================
If CATIA.Documents.Count = 0 Or CATIA.Windows.Count = 0 Then
    MsgBox "Debe tener abierto al menos un documento para utilizar esta herramienta", vbCritical, "Por acá no.."
    Exit Sub
End If

Call PROYECTO(PROY_CODE, PROYS, ARM_SYS)

'NUMEROS ENTEROS PARA TRABAJAR CON PART NUMBERS
'==============================================
Call Param_PN(ARR_PN, PROY_CODE)
intgr_POS_GRUPO = ARR_PN(2)
'==============================================

'SI EL DOCUMENTO ESUN PRODUCTO, SE PASA A MODO DISEŃO
'====================================================
If TypeName(CATIA.ActiveDocument) = "ProductDocument" Then
    CATIA.ActiveDocument.Product.ApplyWorkMode DESIGN_MODE
End If

Call Rutas("PROCESO", RUTA_SALIDA, PROY_CODE)

Set oseleccion = CATIA.ActiveDocument.Selection

'//////////////////////////////////////////////////////////////////////////////////////////////////////////////////////////////////////////////////////////////////
'SI ES UN ARCHIVO PRODUCTO (AGRUPA PARTES Y PRODUCTOS)
'/////////////////////////////////////////////////////////////////////////////////////////////////////////////////////////////////////////////////////////////
If oseleccion.Count > 1 Then

    MsgBox "Sólo se puede REVISAR un P/N a la vez, no sea avaro.", vbCritical, "La avaricia nos va a consumir.."
    Exit Sub
    
ElseIf oseleccion.Count = 1 Then

    'LOOP DESDE 1 HASTA LOS ELEMENTOS SELECCIONADOS
    '==============================================
    For i = 1 To oseleccion.Count
    
        'SI EL TIPO DE DOCUMENTO ES UN PRODUCTO
        '======================================
        If TypeName(oseleccion.ITEM(i).Value) = "Product" Then

            '======================================================================================================================================================
            'SI EL DOCUMENTO GUARDADO ES UNA PARTE
            '======================================================================================================================================================
            If TypeName(oseleccion.ITEM(i).Value.ReferenceProduct.Parent) = "PartDocument" Then
            
                Set part1 = oseleccion.ITEM(i).Value.ReferenceProduct.Parent.Part
                
                Set relationsparte1 = part1.Relations
                            
                Set BodyToRename = oseleccion.ITEM(i).Value.ReferenceProduct.Parent.Part.Bodies.ITEM(1)

                Set parameters1 = part1.Parameters
                
                'PARA PODER REVISAR UNA PARTE SE DEBE PRIMERO REVISAR EL CONJUNTO INMEDIATO SUPERIOR
                '===================================================================================
                
                Call Liberados(ARR_PN_NO_LIBERADO, k_aux)
                
                If NO_LIBERA = True Then
                    MsgBox "Debe revisarse en primer lugar el conjunto inmediato superior.", vbCritical, "Error de secuencia de revisión."
                    Exit Sub
                End If
                
                'DESDE CATIA SE EXTRAEN EL P/N Y LA DESCRIPCIÓN
                '==============================================
                PNAUX = Split(oseleccion.ITEM(i).Value.ReferenceProduct.Parent.Part.Name, "_")
                PN = PNAUX(0)
                DESC = PNAUX(1)
                 
                Grupo = Mid(part1.Name, intgr_POS_GRUPO, 1)
                
                Ruta_Inicial = oseleccion.ITEM(i).Value.ReferenceProduct.Parent.FullName

                Nombre_Inicial = oseleccion.ITEM(i).Value.ReferenceProduct.Parent.Name
                
                Nombre_Archivo = Mid(oseleccion.ITEM(i).Value.ReferenceProduct.Parent.Name, 1, InStr(1, oseleccion.ITEM(i).Value.ReferenceProduct.Parent.Name, ".CATPart") - 1)
                
                'SI EL ARCHIVO COMIENZA POR DD3 SIGNIFICA QUE YA SE HA LIBERADO
                '==============================================================
                If Left(Nombre_Inicial, 3) <> "DD3" And Left(Nombre_Inicial, 2) <> "DF" Then
                    MsgBox "No se puede REVISAR un archivo aún no liberado!" & vbCrLf & vbCrLf & "Considere reemplazar el archivo por uno LIBERADO en documentación técnica.", vbCritical, "Archivo: " & Nombre_Inicial
                    Exit Sub
                End If
                
                Ruta = RUTA_SALIDA & Grupo & "00\3D\"
                
                Archivo_Previo = Ruta & oseleccion.ITEM(i).Value.ReferenceProduct.Parent.Part.Name
    
                Nombre_Liberado = Archivo_Previo & ".CATPart"
                
                EXISTE = CATIA.FileSystem.FileExists(Nombre_Liberado)
                
                If EXISTE = True Then
                    MsgBox "El archivo ya se encuentra con una REVISIÓN en proceso." & vbNewLine & vbNewLine & _
                    "Sólo debe modificarlo y liberarlo.", vbCritical, "Ya existe.."
                    Exit Sub
                End If
                
                'SE ADVIERTE QUE EL ARCHIVO SE VA A LIBERAR
                '==========================================
                Liberacion = MsgBox("Usted está por REVISAR el P/N: " & oseleccion.ITEM(i).Value.ReferenceProduct.Parent.Part.Name & _
                vbCrLf & vbCrLf & "(1)El archivo ya liberado es propiedad de Documentación Tecnica y no se modificará." & vbCrLf & vbCrLf & "(2)La revisión anterior desaparecerá de la visualización de la DMU." _
                , vbOKCancel + vbCritical, "Atención! " & part1.Name)
                If Liberacion = vbOK Then
                    On Error Resume Next
                    oseleccion.ITEM(i).Value.ReferenceProduct.Parent.SaveAs (Nombre_Liberado)
                    
                    'SE GUARDA EL CONJUNTO INMEDIATO SUPERIOR
                    '========================================
                    CATIA.ActiveDocument.Selection.ITEM(1).LeafProduct.Parent.Parent.ReferenceProduct.Parent.Save
                    
                    On Error GoTo 0
                ElseIf Liberacion = vbCancel Then
                    MsgBox "El archivo NO fue revisado", vbCritical, "Alto ahí! " & part1.Name
                    Exit Sub
                End If
                
            '========================================================================================================================================================
            'SI EL DOCUMENTO GUARDADO ES UN PRODUCTO
            '========================================================================================================================================================
            ElseIf TypeName(oseleccion.ITEM(i).Value.ReferenceProduct.Parent) = "ProductDocument" Then
            
                Set product1 = oseleccion.ITEM(i).Value.ReferenceProduct.Parent.Product

                Set parameters1 = product1.Parameters
                
                'PARA PODER REVISAR UNA PARTE SE DEBE PRIMERO REVISAR EL CONJUNTO INMEDIATO SUPERIOR
                '===================================================================================
                
                Call Liberados(ARR_PN_NO_LIBERADO, k_aux)
                
                If NO_LIBERA = True Then
                    MsgBox "Debe revisarse en primer lugar el conjunto inmediato superior.", vbCritical, "Error de secuencia de revisión."
                    Exit Sub
                End If
                
                'DESDE CATIA SE EXTRAEN EL P/N Y LA DESCRIPCIÓN
                '==============================================
                PNAUX = Split(oseleccion.ITEM(i).Value.ReferenceProduct.Parent.Product.Name, "_")
                PN = PNAUX(0)
                DESC = PNAUX(1)
                 
                Grupo = Mid(product1.Name, intgr_POS_GRUPO + 1, 1)
                
                Ruta_Inicial = oseleccion.ITEM(i).Value.ReferenceProduct.Parent.FullName

                Nombre_Inicial = oseleccion.ITEM(i).Value.ReferenceProduct.Parent.Name
                
                Nombre_Archivo = Mid(oseleccion.ITEM(i).Value.ReferenceProduct.Parent.Name, 1, InStr(1, oseleccion.ITEM(i).Value.ReferenceProduct.Parent.Name, ".CATProduct") - 1)
                
                'SI EL ARCHIVO COMIENZA POR DD3 SIGNIFICA QUE YA SE HA LIBERADO
                '==============================================================
                If Left(Nombre_Inicial, 3) <> "DD3" And Left(Nombre_Inicial, 2) <> "DF" Then
                    MsgBox "No se puede REVISAR un archivo aún no liberado!" & vbCrLf & vbCrLf & "Considere reemplazar el archivo por uno LIBERADO en documentación técnica.", vbCritical, "Archivo: " & Nombre_Inicial
                    Exit Sub
                End If
                
                Ruta = RUTA_SALIDA & Grupo & "00\3D\"
                
                Archivo_Previo = Ruta & oseleccion.ITEM(i).Value.ReferenceProduct.Parent.Product.Name
    
                Nombre_Liberado = Archivo_Previo & ".CATProduct"
                
                EXISTE = CATIA.FileSystem.FileExists(Nombre_Liberado)
                
                If EXISTE = True Then
                    MsgBox "El archivo ya se encuentra con una REVISIÓN en proceso." & vbNewLine & vbNewLine & _
                    "Sólo debe modificarlo y liberarlo.", vbCritical, "Ya existe.."
                    Exit Sub
                End If
                
                'SE ADVIERTE QUE EL ARCHIVO SE VA A LIBERAR
                '==========================================
                Liberacion = MsgBox("Usted está por REVISAR el P/N: " & oseleccion.ITEM(i).Value.ReferenceProduct.Parent.Product.Name & _
                vbCrLf & vbCrLf & "(1)El archivo ya liberado es propiedad de Documentación Tecnica y no se modificará." & vbCrLf & vbCrLf & "(2)La revisión anterior desaparecerá de la visualización de la DMU." _
                , vbOKCancel + vbCritical, "Atención! " & product1.Name)
                If Liberacion = vbOK Then
                    On Error Resume Next
                    oseleccion.ITEM(i).Value.ReferenceProduct.Parent.SaveAs (Nombre_Liberado)
                    
                    'SE GUARDA EL CONJUNTO INMEDIATO SUPERIOR
                    '========================================
                    CATIA.ActiveDocument.Selection.ITEM(1).LeafProduct.Parent.Parent.ReferenceProduct.Parent.Save
                    
                    On Error GoTo 0
                ElseIf Liberacion = vbCancel Then
                    MsgBox "El archivo NO fue revisado", vbCritical, "Alto ahí! " & part1.Name
                    Exit Sub
                End If
            
            End If
        
        ElseIf TypeName(oseleccion.ITEM(i).Value) = "Part" Then
        
            MsgBox "Usted a selecionado una parte, debe seleccionar la instancia!" & vbCrLf & " El archivo NO se guardará", vbCritical, "Atencion!!"
        
        End If
    
    Next

'//////////////////////////////////////////////////////////////////////////////////////////////////////////////////////////////////////////////////////////////////
'SI ES UN ARCHIVO INDIVIDUAL
'//////////////////////////////////////////////////////////////////////////////////////////////////////////////////////////////////////////////////////////////////
Else 'SI NO HAY NADA SELECCIONADO

    'NO SE PERMITEN CONGELAR ARCHIVOS INDIVIDUALES DEBIDO A QUE EN EL RE-RUTEO SE PERDERÁ EL ARCHIVO RUTA.
    MsgBox "No se permite REVISAR archivos sin" & vbNewLine & "abrir el conjunto que lo contiene." & vbNewLine & vbNewLine _
    & "Abra el CONJUNTO SUPERIOR INMEDIATO, seleccione" & vbNewLine & "la parte y ejecutenuevamente este comando.", vbCritical, "Debe abrir el CSI.."
    Exit Sub

    'Se verifica el tipo de archivo que esta abierto
    Tipo_Archivo = TypeName(CATIA.ActiveDocument)
    
    '========================================SI EL ARCHIVO ES UN PRODUCTO===============================================================
    '===================================================================================================================================
    If Tipo_Archivo = "ProductDocument" And oseleccion.Count = 0 Then
    
        MsgBox "Seleccione al menos una parte.", vbCritical, "Error Selección"
        Exit Sub
    
    '========================================SI EL ARCHIVO ES UNA PARTE=================================================================
    '===================================================================================================================================
    ElseIf Tipo_Archivo = "PartDocument" Then
    
        MsgBox "Seleccione al menos una parte.", vbCritical, "Error Selección"
        Exit Sub
    
        Set partDocument1 = CATIA.ActiveDocument
        
        Set part1 = partDocument1.Part
        
        Set relationsparte1 = part1.Relations
                    
        Set BodyToRename = partDocument1.Part.Bodies.ITEM(1)
        
        Set parameters1 = part1.Parameters

        Ruta_Inicial = partDocument1.FullName

        Nombre_Inicial = part1.Name
        
        PNAUX = Split(part1.Name, "_")
        PN = PNAUX(0)
        

                
                PNPB_AUX = Split(part1.Name, "_")
                
                PNPB = PNPB_AUX(0)
                
                TIPO_AUX = Split(partDocument1.Name, "-")
                
                TIPO = TIPO_AUX(0)
                
                Nombre_Archivo = Mid(partDocument1.Name, 1, InStr(1, partDocument1.Name, ".CATPart") - 1)
                
                ESTADO = Right(Nombre_Archivo, 12)
                
                'SI EL ARCHIVO COMIENZA POR DD3 SIGNIFICA QUE YA SE HA LIBERADO
                '==============================================================
                If TIPO = "DD3" Then
                    MsgBox "No se puede DESCONGELAR un archivo ya liberado!" & vbCrLf & vbCrLf & "Considere hacer una REVISIÓN", vbCritical, "Archivo: " & Nombre_Inicial
                    Exit Sub
                ElseIf ESTADO <> "PRE-RELEASED" Then
                    MsgBox "El archivo está en PROCESO, usted ya puede modificarlo.", vbCritical, "Archivo: " & Nombre_Inicial
                    Exit Sub
                End If
                
                Ruta = RUTA_SALIDA & Grupo & "00\3D\"
                
                Archivo_Previo = Ruta & part1.Name

                Nombre_Liberado = Archivo_Previo & ".CATPart"
                
                'SE ADVIERTE QUE EL ARCHIVO SE VA A LIBERAR
                '==========================================
                Liberacion = MsgBox("Usted está por DESCONGELAR el P/N: " & part1.Name & _
                vbCrLf & vbCrLf & "(1)El archivo será DESCONGELADO en su estado actual." & vbCrLf & vbCrLf & "(2)Cualquir diseńador PODRÁ modificarlo" _
                , vbOKCancel + vbCritical, "Atención!" & part1.Name)
                
                If Liberacion = vbOK Then
                    On Error Resume Next
                    Err.Clear
                    partDocument1.SaveAs (Nombre_Liberado)
                    
                    'SI HAY UN ERROR EN EL GUARDADO EVITA BORRAR EL ARCHIVO ORIGINAL
                    '================================================================
                    Mata = True
                    If Err.Number <> 0 Then
                        Mata = False
                    End If
                    
                    If Mata = True Then
                        Kill (Ruta_Inicial)
                    Else
                        MsgBox "La parte no ha podido descongelarse debido a que usted no ha aceptado las condiciones de la ventana previa." _
                        & vbNewLine & vbNewLine & "Vuelva a intentarlo.", vbCritical
                        Exit Sub
                    End If
                    On Error GoTo 0
                    
                ElseIf Liberacion = vbCancel Then
                    MsgBox "El archivo NO fue congelado", vbCritical, "Alto ahi! " & part1.Name
                    Exit Sub
                End If
        
    Else
    
    MsgBox "Cosa eh mandinga!! aca pasa algo raro (el archivo no es ni CATPart ni CATProduct)"
    
    End If
    
    'MsgBox Archivo_Existente
    'MsgBox Nombre_Archivo
    'MsgBox part1.Name
End If
    
    
'Else 'USUARIOS
'
'    MsgBox "Usted no está registrado para REVISAR partes.", vbCritical, "Atención! Sr. " & Environ("username")
'
'End If 'USUARIOS
    
End Sub
Public Function ParameterExist(ByRef ParameterCollection As Parameters, ByVal ParameterName As String, ByRef OutputParameter As Parameter) As Boolean
    On Error Resume Next
    Err.Clear
    Set OutputParameter = ParameterCollection.ITEM(ParameterName)
    If Err.Number = 0 Then
        ParameterExist = True
    Else
        ParameterExist = False
    End If
End Function

Attribute VB_Name = "A99_Agregar_Libererias"
'SE CHECKEA LA VERSION DE EXCEL DE LA MAQUINA. SI ES 15.0 CARGA LAS REFERENCIAS PARA ESTA VERSION, SI ES 14.0 CARGA LAS REFERENCIAS PARA ESTA OTRA VERSION.

Sub LibreriasDisponibles(MODE)
 
Dim i As Integer
Dim oExcel As Object 'late binding
Set oExcel = CreateObject("Excel.Application")
 
' retrieve VBE object, the root object that contains all other objects and collections represented in Visual Basic for Applications
Dim oVBE ' As VBE
Set oVBE = CreateObject("MSAPC.Apc").VBE
 
'Use the VBProjects collection to access the collection of projects
Dim project ' As VBProject
Set project = oVBE.ActiveVBProject
 
    'count the number of references selected (to see them go to tools>references)
    'MsgBox "The total number of references selected is: " & project.References.Count
 

    'if you want to loop through all the references to see which ones are selected you could use this.  Be careful though, if there are 100 references selected it will display 100 different message boxes.
    'Dim x As Integer
    'For x = 1 To project.References.Count
    'MsgBox project.References.ITEM(x).Description
    'Next
 
Dim Reference As Object
 
 
If MODE = 1 Then
    '----SI LA VERSION DE EXCEL ES 15.0----
    If oExcel.Application.Version = "15.0" Then
    'MsgBox "Excel is version: " & oExcel.Application.Version
     
        'DEBIDO A QUE LA VERSION DE EXCEL ES LA 15 DEBEMOS REMOVER TODAS LAS REFERENICAS DE LA VERSION 14
        For Each Reference In project.References
           If Reference.Description = "Microsoft PowerPoint 14.0 Object Library" Then
                    project.References.Remove Reference
                    'MsgBox "Referencias para PowerPoint 14.0 encontradas y removidas."
                 Else
           End If
        Next
     
        'SE CHECKEA SI LA LIBRERÍA DE EXCEL 15.0 YA ESTA SELECCIONADA
        i = 0
        For Each Reference In project.References
           If Reference.Description = "Microsoft PowerPoint 15.0 Object Library" Then
                 i = i + 1
                Else
           End If
        Next
     
        If i > 0 Then
            'LA LIBRERÍA DE POWER POINT 15 YA ESTA AGREGADA
            'MsgBox "Librería de PowerPoint 15 ya esta agregada."
        Else
            
            If Dir("C:\Program Files\Microsoft Office 15\Root\Office15\MSPPT.OLB") <> "" Then
                'SE NECESITA AGREGAR LA LIBRERÍA DE POWER POINT 15
                project.References.AddFromFile "C:\Program Files\Microsoft Office 15\Root\Office15\MSPPT.OLB"
                'MsgBox "Librería de PowerPoint 15 agregada."
            Else
                MsgBox "La liberaría de PPT se encuentra en una ruta desconocida. Agregue la ruta a la Macro.", vbCritical
            End If
        End If

    ElseIf oExcel.Application.Version = "14.0" Then
    
        'DEBIDO A QUE LA VERSION DE EXCEL ES LA 14 DEBEMOS REMOVER TODAS LAS REFERENICAS DE LA VERSION 15
        For Each Reference In project.References
           If Reference.Description = "Microsoft PowerPoint 15.0 Object Library" Then
                    project.References.Remove Reference
                    'MsgBox "Referencias para PowerPoint 15.0 encontradas y removidas."
                 Else
           End If
        Next
     
        'SE CHECKEA SI LA LIBRERÍA DE POWERPOINT 14.0 YA ESTA SELECCIONADA
        
        i = 0
        For Each Reference In project.References
           If Reference.Description = "Microsoft PowerPoint 14.0 Object Library" Then
                 i = i + 1
                Else
           End If
        Next
     
        If i > 0 Then
            'LA LIBRERÍA DE POWER POINT 15 YA ESTA AGREGADA
            'MsgBox "Librería de PowerPoint 14.0 ya esta agregada."
        Else

            If Dir("C:\Program Files (x86)\Microsoft Office\Office14\MSPPT.OLB") <> "" Then
                'SE NECESITA AGREGAR LA LIBRERÍA DE POWER POINT 14
                project.References.AddFromFile "C:\Program Files (x86)\Microsoft Office\Office14\MSPPT.OLB"
                'MsgBox "Librería de PowerPoint 15 agregada."
            ElseIf Dir("C:\Program Files\Microsoft Office\Office14\MSPPT.OLB") <> "" Then
                'SE NECESITA AGREGAR LA LIBRERÍA DE POWER POINT 14
                project.References.AddFromFile "C:\Program Files\Microsoft Office\Office14\MSPPT.OLB"
                'MsgBox "Librería de PowerPoint 15 agregada."
            Else
                MsgBox "La liberaría de PPT se encuentra en una ruta desconocida. Agregue la ruta a la Macro.", vbCritical
            End If
        
        End If
    
    
    End If

ElseIf MODE = 2 Then

    '----SI LA VERSION DE EXCEL ES 15.0----
    If oExcel.Application.Version = "15.0" Then
    'MsgBox "Excel is version: " & oExcel.Application.Version
     
        'DEBIDO A QUE LA VERSION DE EXCEL ES LA 15 DEBEMOS REMOVER TODAS LAS REFERENICAS DE LA VERSION 14
        For Each Reference In project.References
           If Reference.Description = "Microsoft PowerPoint 15.0 Object Library" Then
                    project.References.Remove Reference
                    'MsgBox "Referencias para PowerPoint 15.0 encontradas y removidas."
                 Else
           End If
        Next
        
    ElseIf oExcel.Application.Version = "14.0" Then
    
        'DEBIDO A QUE LA VERSION DE EXCEL ES LA 14 DEBEMOS REMOVER TODAS LAS REFERENICAS DE LA VERSION 15
        For Each Reference In project.References
           If Reference.Description = "Microsoft PowerPoint 14.0 Object Library" Then
                    project.References.Remove Reference
                    'MsgBox "Referencias para PowerPoint 14.0 encontradas y removidas."
                 Else
           End If
        Next
    End If


End If
 
End Sub

Attribute VB_Name = "A99_Busca_Palabra_En_Ruta"
Sub BuscaPalabraEnRuta(Ruta, Palabra, parte_encontrada, Modo)
Dim MyFolder As String
Dim MyFile As String
Dim j As Integer

MyFolder = Ruta

If Modo = True Then
    MyFile = Dir(MyFolder & "*.CATPart")
ElseIf Modo = False Then
    MyFile = Dir(MyFolder & "*.CATProduct")
End If

parte_encontrada = False

Do While MyFile <> ""
    j = j + 1
    AUX = InStr(MyFile, Palabra) '1
    Aux2 = InStr(LCase(MyFile), "squele") '1
    If AUX <> 0 And Aux2 = 0 Then
        parte_encontrada = True
    End If
    MyFile = Dir
Loop

End Sub

Attribute VB_Name = "A99_Columnas_EP"
Public COL_LIMITE As Integer
Sub Columnas_EP(ByRef ARR_COLUMNAS() As Variant, COL_LIMITE, PROY_CODE)

Dim Matriz_EP(1 To 150, 1 To 20) As Variant
ReDim ARR_COLUMNAS(1 To 40) As Variant
Dim fsDataFile As Object
Dim sText As Object
Dim sPath As String
Dim sFullLine As String

If PROY_CODE = "" Then
    PROY_CODE = "F5"
End If

Set fsDataFile = CreateObject("Scripting.FileSystemObject")

linea = 0
'The fully qualified path to your lookup file
sPath = "\\srie04in1\Settings_Catia\FADEASA_CATIA\Central_EnvR27\Catalogos\ARCHIVOS_DE_ARRANQUE\PROYECTO\Rutas.csv"

'Create a text stream from your FileSystemObject
Set sText = fsDataFile.OpenTextFile(sPath, 1, False)

'Loop through each line in the text stream
Do While sText.AtEndOfStream <> True
    linea = linea + 1
    sFullLine = sText.ReadLine
    Count = Len(sFullLine) - Len(Replace(sFullLine, ";", ""))
    saCsvData = Split(sFullLine, ";")
    For i = 1 To Count + 1
        Matriz_EP(linea, i) = saCsvData(i - 1)
    Next
Loop

For j = 1 To 15
    If Matriz_EP(2, j) = PROY_CODE Then
        For i = 84 To 105
            ARR_COLUMNAS(i - 83) = Matriz_EP(i, j)
        Next
    End If
Next

COL_LIMITE = ARR_COLUMNAS(1)
For i = 1 To UBound(ARR_COLUMNAS) - 1
    If CInt(COL_LIMITE) < CInt(ARR_COLUMNAS(i + 1)) Then
        COL_LIMITE = ARR_COLUMNAS(i + 1)
    End If
Next

sText.Close

End Sub

Attribute VB_Name = "A99_Generar_Carpetas"
Sub MkCarpetas(BOOL_BORRAR, STR_RUTA_RAIZ, STR_RUTA_PROD, STR_RUTA_PN, REV, LOOP_N, BOOL_ERROR, Ruta_Carpetas, RUTA_ULTIMO_LOOP)

'ESTA SUBRUTINA SE DEFINE PARA CREAR Y ELIMINAR CARPETAS PARA LAS SUCESIVAS CORRECCIONES DENTRO DE UN PROYECTO.
'COMO ENTRADA SE DEFINEN LAS VARIABLES 'BORRAR' QUE SERÁ UNA VARIABLE BOOLEANA Y SERÁ VERDADERA SI DESEAMOS ENTRAR A LA SUBRRUTINA PARA BORRAR UNA RUTA ESPECÍFICA.
'LA VARIABLE 'RAIZ' DEFINE LA RUTA RAIZ DONDE DESEAMOS CREAR LAS SUCESIVAS CARPETAS, LA VARIABLE 'PROD' DEFINE EL NOMBRE DE LA RUTA DEL PRODUCTO CONTENEDOR.
'LA VARIABLE 'PN' DEFINE EL NOMBRE DEL NUMERO DE PARTE QUE SERÁ EL ULTIMO ESLABON EN LA CONFECCIÓN DE LA RUTA

Ruta_CSI = STR_RUTA_RAIZ & STR_RUTA_PROD
Ruta_Carpetas = STR_RUTA_RAIZ & STR_RUTA_PROD & STR_RUTA_PN


'SE VERIFICA SI EL DIRECTORIO HA SIDO CREADO
'============================================
If Dir(Ruta_CSI, vbDirectory) = "" Then
    MkDir (Ruta_CSI)
End If

'SI NO HA SIDO CREADO LA CREA
If Dir(Ruta_Carpetas, vbDirectory) = "" Then
    MkDir (Ruta_Carpetas)
    MkDir (Ruta_Carpetas & "[REV " & REV & "] LOOP_1")
    LOOP_N = 1
'SI HA SIDO CREADO, REVISA EN QUE LOOP SE ENCUENTRA
ElseIf Dir(Ruta_Carpetas, vbDirectory) <> "" Then
    LISTO = False
    For i = 1 To 10 'se admiten 10 loops por revisión
        LOOP_AUX = "[REV " & REV & "] LOOP_" & i
        If Dir(Ruta_Carpetas & LOOP_AUX, vbDirectory) = "" And LISTO = False Then 'si el loop no existe, se crea una carpeta
            LOOP_N = i
            MkDir (Ruta_Carpetas & "[REV " & REV & "] LOOP_" & LOOP_N)
            LISTO = True
        End If
        
        If i = 10 And LISTO = False Then
            MsgBox "Se ha llegado al número máximo de Loops (10). Se recomienda borrar carpetas con LOOPs que no han sido usadas." & vbNewLine, vbCritical
            'se debe salir del la subrutina
            BOOL_ERROR = True
        End If
    Next
End If

RUTA_ULTIMO_LOOP = Ruta_Carpetas & "[REV " & REV & "] LOOP_" & LOOP_N & "\"

End Sub

Attribute VB_Name = "A99_GeoSets_Compuestos"
Sub GeoSetsCompuestos()

Dim fta As HybridBody
Dim fta_ADD As HybridBody
Dim id As HybridBody
Dim gyb As HybridBody
Dim nombre As String

Set doc = CATIA.ActiveDocument
Set PARTE = doc.Part

Do
    n_do = n_do + 1
    NIT_LISTO = True

    NIT = InputBox(vbNewLine & vbNewLine & "Por favor, introduzca cuantos OMLs quiere crear: ", "Superficies de Referencia de Molde", 1)
    
    If StrPtr(NIT) = 0 Then
        Exit Sub
    End If
    
    On Error Resume Next
    Err.Clear
    
    PRUEBA = NIT / 2
    
    If Err.Number <> 0 Then
        MsgBox "El input debe ser numérico entero", vbCritical
        NIT_LISTO = False
    End If
    
    If Len(NIT) > 1 Then
        MsgBox "No se permite agregar tantos OML", vbCritical
        NIT_LISTO = False
    End If
    
    If n_do > 5 Then
        MsgBox "Todos los intentos de asignar cantidad de OMLs fueron fallidos.", vbCritical
        Exit Sub
    End If
    
    NIT = CInt(NIT)
    
Loop While NIT_LISTO = False


On Error Resume Next
'genera geometrical sets...
EXISTE = True
If Len(PARTE.HybridBodies.ITEM("Geometria Auxiliar de Material Compuesto").Name) = 0 Then 'esta declaracion no tiene sentido si no existe el parametro, es solo para que salte el error
    If Err.Number <> 0 Then
    EXISTE = False
    End If
End If
On Error GoTo 0


If EXISTE = False Then
    Set fta = PARTE.HybridBodies.Add
    fta.Name = "Geometria Auxiliar de Material Compuesto"
    Set fta_ADD = PARTE.HybridBodies.ITEM("Geometria Auxiliar de Material Compuesto")
Else
    Set fta_ADD = PARTE.HybridBodies.ITEM("Geometria Auxiliar de Material Compuesto")
End If


For i = 1 To NIT
    On Error Resume Next
    EXISTE_OML = True
    If Len(PARTE.HybridBodies.ITEM("OML_" & i).Name) = 0 Then 'esta declaracion no tiene sentido si no existe el parametro, es solo para que salte el error
        If Err.Number <> 0 Then
        EXISTE_OML = False
        End If
    End If
    On Error GoTo 0
    
    If EXISTE_OML = False Then
        Set fta = PARTE.HybridBodies.Add
        fta.Name = "OML_" & i
    Else
        Set fta = PARTE.HybridBodies.ITEM("OML_" & i)
    End If
Next

For i = 1 To NIT
    On Error Resume Next
    EXISTE_EOP = True
    If Len(PARTE.HybridBodies.ITEM("EOP_" & i).Name) = 0 Then 'esta declaracion no tiene sentido si no existe el parametro, es solo para que salte el error
        If Err.Number <> 0 Then
        EXISTE_EOP = False
        End If
    End If
    On Error GoTo 0

    If EXISTE_EOP = False Then
        Set fta = PARTE.HybridBodies.Add
        fta.Name = "EOP_" & i
    Else
        Set fta = PARTE.HybridBodies.ITEM("EOP_" & i)
    End If
Next
    
For i = 1 To NIT
    On Error Resume Next
    EXISTE_ROS = True
    If Len(PARTE.HybridBodies.ITEM("ROSETTE OML_" & i).Name) = 0 Then 'esta declaracion no tiene sentido si no existe el parametro, es solo para que salte el error
        If Err.Number <> 0 Then
        EXISTE_ROS = False
        End If
    End If
    On Error GoTo 0
    
    If EXISTE_ROS = False Then
        Set fta = PARTE.HybridBodies.Add
        fta.Name = "ROSETTE OML_" & i
    Else
        Set fta = PARTE.HybridBodies.ITEM("ROSETTE OML_" & i)
    End If
Next

    
On Error Resume Next
'genera geometrical sets...

EXISTE = True
Err.Clear
If Len(fta_ADD.HybridBodies.ITEM("PG 1").Name) = 0 Then 'esta declaracion no tiene sentido si no existe el parametro, es solo para que salte el error
    If Err.Number <> 0 Then
    EXISTE = False
    End If
End If
On Error GoTo 0

If EXISTE = False Then
    Set id = fta_ADD.HybridBodies.Add
    id.Name = "PG 1"
End If

On Error Resume Next
'genera geometrical sets...
EXISTE = True
If Len(fta_ADD.HybridBodies.ITEM("PG 2").Name) = 0 Then 'esta declaracion no tiene sentido si no existe el parametro, es solo para que salte el error
    If Err.Number <> 0 Then
    EXISTE = False
    End If
End If
On Error GoTo 0

If EXISTE = False Then
    Set gyb = fta_ADD.HybridBodies.Add
    gyb.Name = "PG 2"
End If

On Error Resume Next
'genera geometrical sets...
EXISTE = True
If Len(fta_ADD.HybridBodies.ITEM("PG 3").Name) = 0 Then 'esta declaracion no tiene sentido si no existe el parametro, es solo para que salte el error
    If Err.Number <> 0 Then
    EXISTE = False
    End If
End If
On Error GoTo 0

If EXISTE = False Then
    Set view_1 = fta_ADD.HybridBodies.Add
    view_1.Name = "PG 3"
End If



End Sub

Attribute VB_Name = "A99_Liberados_Check"
Sub Liberados(ByRef ARR_PN_NO_LIBERADO() As String, k_aux)

Dim Archivo_Existente As Variant
Dim RUTA_SALIDA As String
Dim Nombre_Ruta As String
Dim Nombre_Ruta_Archivo_Guardado As String
Dim Nombre_Archivo As String
Dim Tipo_Archivo As String
Dim Nom_PartProd As String
Dim producto As Product
Dim relationsproducto1 As Relations
Dim productDocument1 As ProductDocument
Dim product1 As Product
Dim partDocument1 As PartDocument
Dim part1 As Part
Dim relationsparte1 As Relations
Dim oseleccion As Selection

Call PROYECTO(PROY_CODE, PROYS, ARM_SYS)

'SE BUSCA SI LAS RUTAS DE LOS ARCHIVOS COINCIDEN CON LAS SIGUIENTES
'==================================================================
TIPO = "PROCESO"
Call Rutas(TIPO, RUTA_SALIDA, PROY_CODE)
Ruta_Proceso = RUTA_SALIDA

TIPO = "DD3"
Call Rutas(TIPO, RUTA_SALIDA, PROY_CODE)
Ruta_Liberado = RUTA_SALIDA

TIPO = "COM_FADEA"
Call Rutas(TIPO, RUTA_SALIDA, PROY_CODE)
Ruta_Comerciales_Fadea = RUTA_SALIDA

TIPO = "COM_PROY"
Call Rutas(TIPO, RUTA_SALIDA, PROY_CODE)
Ruta_Comerciales_Proy = RUTA_SALIDA

TIPO = "DF"
Call Rutas(TIPO, RUTA_SALIDA, PROY_CODE)
Ruta_DF = RUTA_SALIDA
'==================================================================

NO_LIBERA = True



'SI SOLAMENTE TENEMOS ABIERTA UNA PARTE, SE SALTA EL CAMBIO DE NOMBRE DE INSTANCIAS
'==================================================================================
If TypeName(CATIA.ActiveDocument.Selection.ITEM(1).Value.ReferenceProduct.Parent) = "ProductDocument" Then
    
    CATIA.ActiveDocument.Product.ApplyWorkMode DESIGN_MODE
    
    'REFERENCIAS PARA REVISAR TODOS LOS COMPONENTES DEL PRODUCTO
    '===========================================================
    Dim oTopProductDoc As ProductDocument
    Dim oTopProduct As Product
    Dim INumberOfItems As Long
    
    Set oTopProductDoc = CATIA.ActiveDocument.Selection.ITEM(1).Value.ReferenceProduct.Parent
    Set oTopProduct = oTopProductDoc.Product
    
    INumberOfItems = oTopProduct.Products.Count
        
    'SI SE ENCUENTRA EL ARCHIVO DENTRO DE ALGUNA DE LAS RUTAS SE PERMITE LIBERAR
    'EN EL CASO DE QUE EL ARCHIVO NO ESTÉ EN NINGUNA DE ESTAS RUTAS, SIGNIFICA QUE
    'NO ESTA LIBERADO DE NINGUNA MANERA(COMO DF O INCORPORADO) O NO ES UN COMERCIAL
    '=============================================================================
    k_aux = 0
    For k = 1 To INumberOfItems
        On Error Resume Next
            If Not ProductIsComponent(oTopProduct.Products.ITEM(k)) Then
                If InStr(1, UCase(oTopProduct.Products.ITEM(k).ReferenceProduct.Parent.FullName), UCase(Ruta_Liberado)) > 0 Then
                    NO_LIBERA = False
                ElseIf InStr(1, UCase(oTopProduct.Products.ITEM(k).ReferenceProduct.Parent.FullName), UCase(Ruta_Comerciales_Fadea)) > 0 Then
                    NO_LIBERA = False
                ElseIf InStr(1, UCase(oTopProduct.Products.ITEM(k).ReferenceProduct.Parent.FullName), UCase(Ruta_Comerciales_Proy)) > 0 Then
                    NO_LIBERA = False
                ElseIf InStr(1, UCase(oTopProduct.Products.ITEM(k).ReferenceProduct.Parent.FullName), UCase(Ruta_DF)) > 0 Then
                    NO_LIBERA = False
                Else
                    NO_LIBERA = True
                    k_aux = k_aux + 1
                End If
            End If
        On Error GoTo 0
        
        If NO_LIBERA = True Then
            ARR_PN_NO_LIBERADO(k_aux) = oTopProduct.Products.ITEM(k).ReferenceProduct.Parent.Name
        End If

    Next 'k

If k_aux > 0 Then
    NO_LIBERA = True
End If

ElseIf TypeName(CATIA.ActiveDocument.Selection.ITEM(1).Value.ReferenceProduct.Parent) = "PartDocument" Then
    
    REVISAR = UCase(CATIA.ActiveDocument.Selection.ITEM(1).LeafProduct.Parent.Parent.ReferenceProduct.Parent.FullName)
    'SI SE ENCUENTRA QUE EL CONJUNTO INMEDIATO SUPERIOR DE LA PARTE NO ESTÁ EN LA CARPETA PROCESOS
    If InStr(1, UCase(CATIA.ActiveDocument.Selection.ITEM(1).LeafProduct.Parent.Parent.ReferenceProduct.Parent.FullName), UCase(Ruta_Proceso)) > 0 Then
        NO_LIBERA = False
    End If

End If

End Sub

Function ProductIsComponent(iProduct) As Boolean

Set objDoc = iProduct.ReferenceProduct.Parent
Set objParentDoc = iProduct.Parent.Parent.ReferenceProduct.Parent
ProductIsComponent = (objDoc Is objParentDoc)

End Function

Attribute VB_Name = "A99_PN_Excel_Check"
Sub PN_EN_TABLA(N_PARTE, no_pn)

Call PROYECTO(PROY_CODE, PROYS, ARM_SYS)

Set OBJXL = CreateObject("Excel.Application")
Call Rutas("ESTRUCTURA", RUTA_SALIDA, PROY_CODE)
Datei = RUTA_SALIDA
OBJXL.Workbooks.Open FileName:=Datei, ReadOnly:=True
OBJXL.Visible = False
OBJXL.ActiveSheet.Activate

Call Columnas_EP(ARR_COLUMNAS, COL_LIMITE, PROY_CODE)
Call Param_PN(ARR_PN, PROY_CODE)

no_pn = False

For i = 1 To 3000
    If UCase(N_PARTE) = UCase(OBJXL.Worksheets(1).Cells(i, ARR_COLUMNAS(2))) Then
        'SE DECLARA QUE ENTRÓ (HUBO COINCIDENCIA)
        no_pn = True
    End If
Next

AUX_EXCEL = Split(RUTA_SALIDA, "\")
OBJXL.Workbooks(AUX_EXCEL(UBound(AUX_EXCEL))).Close SaveChanges:=False

End Sub

Attribute VB_Name = "A99_PN_REV_Check"
'AUTOR: SEBASTIAN ASSAIN
'NOMBRE: A99_PN_REV_Check
'VERSION 1.0
'FECHA: 25/05/2022
'CAMBIOS: SE AGREGA PartProd PARA DISTINGUIR ENTRE TIPOS DE ARCHIVOS.
'FRASE: SI SUBÍS A SMITH Y A MARX EN EL MISMO BARCO, SEGURAMENTE UNO VA A QUERER IR HACIA EL SUR Y EL OTRO HACIA EL NORTE.
'       AHORA, SI EL BARCO SE EMPIEZA A INUNDAR, AMBOS VAN A AGARRAR U BALDE Y A SACAR AGUA HACIA AFUERA.
'DESCRIPCIÓN: OTORGA LA SIGUIENTE EDICIÓN DISPONIBLE

Sub REV_PN(RUTA_REV, N_PARTE, TIPO, REV, N_DF, PartProd)

If PartProd = "PARTE" Then
    STR_EXTENSION = ".CATPart"
ElseIf PartProd = "PRODUCTO" Then
    STR_EXTENSION = ".CATProduct"
End If

EXISTE = CATIA.FileSystem.FileExists(RUTA_REV & TIPO & "-" & N_PARTE & "-" & "A" & STR_EXTENSION)

'SE VERIFICA LA ULTIMA EDICIÓN ENCONTRADA
'=========================================
If EXISTE = True Then
    Existe_Aux = False
    For k = 65 To 90
        Existe_Aux = CATIA.FileSystem.FileExists(RUTA_REV & TIPO & "-" & N_PARTE & "-" & Chr(k) & STR_EXTENSION)
        If Existe_Aux = True Then
            REV = Chr(k + 1)
        End If
    Next
ElseIf EXISTE = False Then
    REV = "A"
End If

'SE VERIFICA EL ULTIMO INDICE 'DF' ENCONTRADO
'============================================
Dim N_DF_AUX As Integer
N_DF = 1
Existe_Aux_2 = False
For N_DF_AUX = 1 To 9 'intenta encontrar todos los DF cargados para un numero de parte y una revisión específica
    Existe_Aux = CATIA.FileSystem.FileExists(RUTA_REV & TIPO & N_DF_AUX & "-" & N_PARTE & "-" & REV & STR_EXTENSION)
    If Existe_Aux = True Then
        N_DF = N_DF_AUX + 1
        Existe_Aux_2 = True
    End If
Next

If TIPO = "DD3" Then
    N_DF = ""
End If

End Sub

Attribute VB_Name = "A99_Param_Check"
Public Param_List(1 To 50, 1 To 10) As String
Public PN_CATIA As String
Public PN_RUTA As String
Public NO_LIBERA As Boolean
Public PUB_BODY As String
Public BOOL_PARTE As String

Sub Param_Check(REV)

Dim Archivo_Existente As Variant
Dim Ruta As String
Dim RUTA_SALIDA As String
Dim Nombre_Ruta As String
Dim Nombre_Ruta_Archivo_Guardado As String
Dim Nombre_Archivo As String
Dim Tipo_Archivo As String
Dim Nom_PartProd As String
Dim producto As Product
Dim relationsproducto1 As Relations
Dim productDocument1 As ProductDocument
Dim product1 As Product
Dim partDocument1 As PartDocument
Dim part1 As Part
Dim relationsparte1 As Relations
Dim oseleccion As Selection
Dim strParam1 As StrParam
Dim parameters1 As Parameters
Dim Param As Parameter
Dim publications1 As Publications

PUB_BODY = "FALTA"

If CATIA.ActiveDocument.Selection.Count = 0 Then
    If TypeName(CATIA.ActiveDocument) = "PartDocument" Then
        Set partDocument1 = CATIA.ActiveDocument
        Set part1 = partDocument1.Part
        Set relationsparte1 = part1.Relations
        Set parameters1 = part1.Parameters
        Set publications1 = CATIA.ActiveDocument.GetItem(part1.Name).Publications
        DESCAUX = Split(part1.Name, "_")
        PN_CATIA = part1.Name
        PN_RUTA = Mid(CATIA.ActiveDocument.Name, 1, InStr(1, CATIA.ActiveDocument.Name, ".CATPart") - 1)
        On Error Resume Next
        Err.Clear
        If publications1.ITEM(1).Name = PN Then
            PUB_BODY = "OK"
        End If
        If Err.Number <> 0 Then
            PUB_BODY = "FALTA"
        End If
        On Error GoTo 0
        BOOL_PARTE = True
    ElseIf TypeName(CATIA.ActiveDocument) = "ProductDocument" Then
        Set productDocument1 = CATIA.ActiveDocument
        Set product1 = productDocument1.Product
        Set parameters1 = product1.Parameters
        DESCAUX = Split(product1.Name, "_")
        PN_CATIA = product1.Name
        PN_RUTA = Mid(CATIA.ActiveDocument.Name, 1, InStr(1, CATIA.ActiveDocument.Name, ".CATProduct") - 1)
        BOOL_PARTE = False
    Else
        MsgBox "Los parámetros de este tipo de documentos no están contemplados para ser chequeados.", vbInformation, "Alcance de macro insuficiente."
        Exit Sub
    End If
ElseIf CATIA.ActiveDocument.Selection.Count = 1 Then
    If TypeName(CATIA.ActiveDocument.Selection.ITEM(1).Value.ReferenceProduct.Parent) = "PartDocument" Then
        Set oseleccion = CATIA.ActiveDocument.Selection
        Set part1 = oseleccion.ITEM(1).Value.ReferenceProduct.Parent.Part
        Set relationsparte1 = part1.Relations
        Set parameters1 = part1.Parameters
        PNAUX = Split(oseleccion.ITEM(1).Value.ReferenceProduct.Parent.Part.Name, "_")
        PN_CATIA = part1.Name
        PN_RUTA = Mid(CATIA.ActiveDocument.Selection.ITEM(1).Value.ReferenceProduct.Parent.Name, 1, InStr(1, CATIA.ActiveDocument.Selection.ITEM(1).Value.ReferenceProduct.Parent.Name, ".CATPart") - 1)
        On Error Resume Next
        Set product1 = oseleccion.ITEM(1).Value.ReferenceProduct.Parent.GetItem(oseleccion.ITEM(1).Value.ReferenceProduct.Parent.Part.Name)
        Set publications1 = product1.Publications
        Err.Clear
        If oseleccion.ITEM(1).Value.Publications.ITEM(PNAUX(0)).Name = PNAUX(0) Then
            PUB_BODY = "OK"
        End If
        If Err.Number <> 0 Then
            PUB_BODY = "FALTA"
        End If
        On Error GoTo 0
        BOOL_PARTE = True
    ElseIf TypeName(CATIA.ActiveDocument.Selection.ITEM(1).Value.ReferenceProduct.Parent) = "ProductDocument" Then
        Set oseleccion = CATIA.ActiveDocument.Selection
        Set product1 = oseleccion.ITEM(1).Value.ReferenceProduct.Parent.Product
        Set parameters1 = product1.Parameters
        PNAUX = Split(oseleccion.ITEM(1).Value.ReferenceProduct.Parent.Product.Name, "_")
        PN_CATIA = product1.Name
        PN_RUTA = Mid(CATIA.ActiveDocument.Selection.ITEM(1).Value.ReferenceProduct.Parent.Name, 1, InStr(1, CATIA.ActiveDocument.Selection.ITEM(1).Value.ReferenceProduct.Parent.Name, ".CATProduct") - 1)
        BOOL_PARTE = False
    Else
        MsgBox "Los parámetros de este tipo de documentos no están contemplados para ser chequeados.", vbInformation, "Alcance de macro insuficiente."
        Exit Sub
    End If
Else
    Exit Sub
End If

Call Param_Read(Param_List, REV)

If BOOL_PARTE = True Then
    For i = 1 To UBound(Param_List)
        If ParameterExist(parameters1, Param_List(i, 1), Param) Then
            Param_List(i, 2) = "OK"
            If InStr(1, Param_List(i, 1), "IMI_") = 0 Then
                If Param.Value = "" Or Param.Value = 0 Then '<--- SI LOS PARÁMETROS SON NULOS O ESTAN VACÍOS SE CONSIDERA INCOMPLETO
                    Param_List(i, 3) = "INCOMPLETO"
                Else
                    Param_List(i, 3) = "OK"
                    Param_List(i, 4) = Param.ValueAsString
                End If
            Else '<---------------------------------------------- EL PARÁMETRO IMI ADMITE QUE SU VALOR SEA 00, POR LO QUE SÓLO EN ESTE CASO SE DÁ POR CORRECTO EL VALOR NULO.
                If Param.Value = "" Then
                    Param_List(i, 3) = "INCOMPLETO"
                Else
                    Param_List(i, 3) = "OK"
                    Param_List(i, 4) = Param.ValueAsString
                End If
            End If
        Else
            Param_List(i, 2) = "FALTA"
            Param_List(i, 3) = "FALTA"
        End If
    Next
Else
    For i = 1 To UBound(Param_List)
        If ParameterExist(parameters1, product1.Name & "\" & Param_List(i, 1), Param) Then
            Param_List(i, 2) = "OK"
            If InStr(1, Param_List(i, 1), "IMI_") = 0 Then
                If Param.Value = "" Or Param.Value = 0 Then '<--- SI LOS PARÁMETROS SON NULOS O ESTAN VACÍOS SE CONSIDERA INCOMPLETO
                    Param_List(i, 3) = "INCOMPLETO"
                Else
                    Param_List(i, 3) = "OK"
                    Param_List(i, 4) = Param.ValueAsString
                End If
            Else '<---------------------------------------------- EL PARÁMETRO IMI ADMITE QUE SU VALOR SEA 00, POR LO QUE SÓLO EN ESTE CASO SE DÁ POR CORRECTO EL VALOR NULO.
                If Param.Value = "" Then
                    Param_List(i, 3) = "INCOMPLETO"
                Else
                    Param_List(i, 3) = "OK"
                    Param_List(i, 4) = Param.ValueAsString
                End If
            End If
        Else
            Param_List(i, 2) = "FALTA"
            Param_List(i, 3) = "FALTA"
        End If
    Next
End If

UserForm92.Show

End Sub

Public Function ParameterExist(ByRef ParameterCollection As Parameters, ByVal ParameterName As String, ByRef OutputParameter As Parameter) As Boolean
    On Error Resume Next
    Err.Clear
    Set OutputParameter = ParameterCollection.ITEM(ParameterName)
    If Err.Number = 0 Then
        ParameterExist = True
    Else
        ParameterExist = False
    End If
End Function

Attribute VB_Name = "A99_Param_Mov"
Sub Parametro_Mov(PART_FROM, BODY_TO, PARAMETER_NAME)

Dim partDocument1 As PartDocument
Set partDocument1 = CATIA.ActiveDocument

Dim selection1 As Selection
Set selection1 = partDocument1.Selection

selection1.Clear

Dim part1 As Part
Set part1 = partDocument1.Part

Dim parameters1 As Parameters
Set parameters1 = part1.Parameters

Dim intParam1 As IntParam
Set intParam1 = parameters1.ITEM(PART_FROM & "\" & PARAMETER_NAME)

selection1.Add intParam1

selection1.Cut

Set partDocument1 = CATIA.ActiveDocument

Dim selection2 As Selection
Set selection2 = partDocument1.Selection

selection2.Clear

Dim bodies1 As Bodies
Set bodies1 = part1.Bodies

Dim body1 As Body
Set body1 = bodies1.ITEM(BODY_TO)

selection2.Add body1

selection2.Paste

End Sub

Attribute VB_Name = "A99_Param_PN"
Sub Param_PN(ByRef ARR_PN() As Variant, PROY_CODE)

Dim Matriz_PN(1 To 150, 1 To 20) As Variant
ReDim ARR_PN(1 To 40) As Variant
Dim fsDataFile As Object
Dim sText As Object
Dim sPath As String
Dim sFullLine As String

If PROY_CODE = "" Then
    PROY_CODE = "F5"
End If

Set fsDataFile = CreateObject("Scripting.FileSystemObject")

linea = 0
'The fully qualified path to your lookup file
sPath = "\\srie04in1\Settings_Catia\FADEASA_CATIA\Central_EnvR27\Catalogos\ARCHIVOS_DE_ARRANQUE\PROYECTO\Rutas.csv"

'Create a text stream from your FileSystemObject
Set sText = fsDataFile.OpenTextFile(sPath, 1, False)

'Loop through each line in the text stream
Do While sText.AtEndOfStream <> True
    linea = linea + 1
    sFullLine = sText.ReadLine
    Count = Len(sFullLine) - Len(Replace(sFullLine, ";", ""))
    saCsvData = Split(sFullLine, ";")
    For i = 1 To Count + 1
        Matriz_PN(linea, i) = saCsvData(i - 1)
    Next
Loop


For j = 1 To 15
    If Matriz_PN(2, j) = PROY_CODE Then
        For i = 3 To 9
            ARR_PN(i - 2) = Matriz_PN(i, j)
        Next
    End If
Next

sText.Close

End Sub

Attribute VB_Name = "A99_Param_Read"
Sub Param_Read(Param_List, REV)

Dim Matriz_PARAM(100, 50) As Variant
'Dim Param_List(1 To 30, 1 To 2) As String
Dim fsDataFile As Object
Dim sText As Object
Dim sPath As String
Dim sFullLine As String

'LECTURA DE LOS CÓDIGOS
Call PROYECTO(PROY_CODE, PROYS, ARM_SYS)

'Dim MAT_CODE(1000, 44) As Variant
Call Rutas("PARAMETROS", RUTA_SALIDA, PROY_CODE)

Set fsDataFile = CreateObject("Scripting.FileSystemObject")
'The fully qualified path to your lookup file
sPath = RUTA_SALIDA

'Create a text stream from your FileSystemObject
Set sText = fsDataFile.OpenTextFile(sPath, 1, False)

'Loop through each line in the text stream
j = 0
Do While sText.AtEndOfStream <> True
    linea = linea + 1
    sFullLine = sText.ReadLine
    saCsvData = Split(sFullLine, ";")
    
    j = j + 1
    For i = 0 To UBound(saCsvData)
        Matriz_PARAM(j, i) = saCsvData(i)
    Next
    
Loop

For i = 2 To 30
    
    If InStr(1, Matriz_PARAM(i, 0), "IMI") > 0 Then
        Param_List(i - 1, 1) = Matriz_PARAM(i, 0) & REV
    ElseIf InStr(1, Matriz_PARAM(i, 0), "FECHA") > 0 Then
        Param_List(i - 1, 1) = Matriz_PARAM(i, 0) & REV
    ElseIf InStr(1, Matriz_PARAM(i, 0), "REV_") > 0 Then
        Param_List(i - 1, 1) = Matriz_PARAM(i, 0) & REV
    Else
        Param_List(i - 1, 1) = Matriz_PARAM(i, 0)
    End If
    
    Param_List(i - 1, 2) = Matriz_PARAM(i, 1)

Next

End Sub

Attribute VB_Name = "A99_Proyecto"
Sub PROYECTO(PROY_CODE, ByRef PROYS() As Variant, ARM_SYS)

Dim AUX_PROYS(1 To 20) As Variant
Dim Rutas_Proyecto(1 To 150, 1 To 20) As Variant
Dim fsDataFile As Object
Dim sText As Object
Dim sPath As String
Dim sFullLine As String

Set fsDataFile = CreateObject("Scripting.FileSystemObject")

linea = 0
'The fully qualified path to your lookup file
sPath = "\\srie04in1\Settings_Catia\FADEASA_CATIA\Central_EnvR27\Catalogos\ARCHIVOS_DE_ARRANQUE\PROYECTO\Rutas.csv"

'Create a text stream from your FileSystemObject
Set sText = fsDataFile.OpenTextFile(sPath, 1, False)

'Loop through each line in the text stream
Do While sText.AtEndOfStream <> True
    linea = linea + 1
    sFullLine = sText.ReadLine
    Count = Len(sFullLine) - Len(Replace(sFullLine, ";", ""))
    saCsvData = Split(sFullLine, ";")
    For i = 1 To Count + 1
        Rutas_Proyecto(linea, i) = saCsvData(i - 1)
    Next
Loop
    
'SE OBTIENE EL PROYECTO ACTUAL, SI NO HAY NADA ABIERTO SE SELECCIONA EL PRIMER PROYECTO QUE SE ENCUENTRA EN "Rutas.csv"
'======================================================================================================================
If CATIA.Documents.Count = 0 Or CATIA.Windows.Count = 0 Then
    PROY_CODE = Rutas_Proyecto(2, 2)
Else
    For j = 2 To 15
        If Rutas_Proyecto(2, j) <> "" Then
            If InStr(1, CATIA.ActiveDocument.Name, Rutas_Proyecto(2, j)) <> 0 Then
                PROY_CODE = Rutas_Proyecto(2, j)
                ARM_SYS = Rutas_Proyecto(1, j)
            End If
        End If
    Next
End If

'SI SE TRATA DE UN DRAWING CREADO POR LA MACRO DEBERÁ TENER LE PARÁMETRO DE NUMERO DE PARTE ASIGNADO
'===================================================================================================
If CATIA.Documents.Count = 0 Or CATIA.Windows.Count = 0 Then
    PROY_CODE = Rutas_Proyecto(2, 2)
ElseIf TypeName(CATIA.ActiveDocument) = "DrawingDocument" Then
    Dim drawingDocument1 As DrawingDocument
    Set drawingDocument1 = CATIA.ActiveDocument
    Set parameters1 = drawingDocument1.Parameters
    For j = 2 To 15
        If Rutas_Proyecto(2, j) <> "" Then
            For i = 1 To parameters1.Count
                If InStr(1, parameters1.ITEM(i).Value, Rutas_Proyecto(2, j)) <> 0 Then
                    PROY_CODE = Rutas_Proyecto(2, j)
                    ARM_SYS = Rutas_Proyecto(1, j)
                End If
            Next
        End If
    Next
    
End If

'OBTIENE LOS PARAMETROS FIJOS PARA TODOS LOS PROYECTOS
'=====================================================
NUM = 0
For j = 2 To 15
    If Rutas_Proyecto(2, j) <> "" Then
        NUM = NUM + 1
        AUX_PROYS(NUM) = Rutas_Proyecto(2, j)
    End If
Next

'SI NO ENCUENTRA EL PROYECTO ASIGNA EL PRIMER PROYECTO QUE SE ENCUENTRA EN "Rutas.csv"
'=====================================================================================
If PROY_CODE = "" Then
    PROY_CODE = Rutas_Proyecto(2, 2)
End If

ReDim PROYS(1 To NUM)

For k = 1 To NUM
    PROYS(k) = AUX_PROYS(k)
Next

End Sub

Attribute VB_Name = "A99_Recorrido_Arbol"
'************************************************************************************************
'
' Description: This macro loops through all nodes a product tree and informs the user as to
'              the node's "type" - part, product or component.  This is done as follows:
'
'               1. The tree is looped through by use of a recursive call to the GetNextNode sub
'
'               2. Thenode "type" is determine by attempting to set the node to either a *.CATPart
'                  or *.CATProduct filename
'
' Assumptions: 1. Active document must be a catia product
'
'   Developer: Brian Roach
'
'        Date: 5JAN2007
'
' CATIA Level: V5R14 SP8
'
'************************************************************************************************
Public NODO As String
Public PN_PROP(10000, 21) As Variant
Public PN_DEPUR(10000, 21) As Variant
Public N_ITEM As Integer

Sub RecorridoArbol()
    
    Call PROYECTO(PROY_CODE, PROYS, ARM_SYS)
    
    Erase PN_PROP
    Erase PN_DEPUR
    
    'SI NO EXISTE NINGUN DOCUMENTO ABIERTO SE EVITA QUE LA MACRO DEVUELVA UN ERROR
    '=============================================================================
    If CATIA.Documents.Count = 0 Or CATIA.Windows.Count = 0 Then
        MsgBox "Debe tener abierto al menos un documento para utilizar esta herramienta.", vbCritical, "Por acá no.."
        Exit Sub
    End If
    
    CATIA.ActiveDocument.Product.ApplyWorkMode DESIGN_MODE
    
    NODO = 0
    N_ITEM = 1
    N_PROD = 0
    
    PN_COMPLETO = Mid(CATIA.ActiveDocument.Name, 1, InStr(1, CATIA.ActiveDocument.Name, ".") - 1)
    DESCAUX = Split(PN_COMPLETO, "_")
    PN = DESCAUX(0)
    DESC = DESCAUX(1)
    
    On Error Resume Next
    PN_PROP(N_ITEM, 1) = PN_COMPLETO
    PN_PROP(N_ITEM, 2) = ""
    PN_PROP(N_ITEM, 3) = CATIA.ActiveDocument.Product.Parameters.RootParameterSet.DirectParameters.ITEM("Nivel").ValueAsString
    PN_PROP(N_ITEM, 4) = CATIA.ActiveDocument.Product.Parameters.RootParameterSet.DirectParameters.ITEM("Cantidad").ValueAsString
    PN_PROP(N_ITEM, 5) = PN
    PN_PROP(N_ITEM, 6) = "0"
    PN_PROP(N_ITEM, 7) = CATIA.ActiveDocument.Product.Parameters.RootParameterSet.DirectParameters.ITEM("Autor").ValueAsString
    PN_PROP(N_ITEM, 8) = CATIA.ActiveDocument.Product.Parameters.RootParameterSet.DirectParameters.ITEM("Estado").ValueAsString
    PN_PROP(N_ITEM, 9) = CATIA.ActiveDocument.Product.Parameters.RootParameterSet.DirectParameters.ITEM("Tipo").ValueAsString
    PN_PROP(N_ITEM, 10) = "N/A"
    PN_PROP(N_ITEM, 11) = ""
    PN_PROP(N_ITEM, 12) = "N/A"
    PN_PROP(N_ITEM, 13) = "N/A"
    PN_PROP(N_ITEM, 14) = "N/A"
    PN_PROP(N_ITEM, 15) = CATIA.ActiveDocument.Product.Parameters.RootParameterSet.DirectParameters.ITEM("ING. FABRIC.").ValueAsString
    PN_PROP(N_ITEM, 16) = CATIA.ActiveDocument.Product.Parameters.RootParameterSet.DirectParameters.ITEM("REVISÓ").ValueAsString
    PN_PROP(N_ITEM, 17) = CATIA.ActiveDocument.Product.Parameters.RootParameterSet.DirectParameters.ITEM("ING. SISTEMAS").ValueAsString
    PN_PROP(N_ITEM, 18) = CATIA.ActiveDocument.Product.Parameters.RootParameterSet.DirectParameters.ITEM("VER. RESIST.").ValueAsString
    PN_PROP(N_ITEM, 19) = CATIA.ActiveDocument.Product.Parameters.RootParameterSet.DirectParameters.ITEM("APROBÓ").ValueAsString
    PN_PROP(N_ITEM, 20) = NODO
    On Error GoTo 0
    
    Call GetNextNode(CATIA.ActiveDocument.Product, NODO, PN_PROP, N_ITEM, N_PROD)
      
'GENERAR TXT DE CADA ARCHIVO
 
    'EXCEL
    '=====
    Dim ExcelLate As Object

    On Error Resume Next
    Set ExcelLate = GetObject("Excel.Application")

    If Err.Number <> 0 Then
        Set ExcelLate = CreateObject("Excel.Application")
    End If
    On Error GoTo 0

    Set Wbook = ExcelLate.Workbooks.Add
    ExcelLate.Visible = False

    Debug.Print

    Wbook.Sheets(1).Cells(1, 2) = "NIVEL LOCAL"
    Wbook.Sheets(1).Cells(1, 3) = "NOMBRE COMPLETO"
    Wbook.Sheets(1).Cells(1, 4) = "INSTANCIA"
    Wbook.Sheets(1).Cells(1, 5) = "NIVEL GLOBAL"
    Wbook.Sheets(1).Cells(1, 6) = "CANTIDAD"
    Wbook.Sheets(1).Cells(1, 7) = "NUMERO DE PARTE"
    Wbook.Sheets(1).Cells(1, 8) = "NRO. ORD."
    Wbook.Sheets(1).Cells(1, 9) = "AUTOR"
    Wbook.Sheets(1).Cells(1, 10) = "ESTADO"
    Wbook.Sheets(1).Cells(1, 11) = "TECNOLOGIA"
    Wbook.Sheets(1).Cells(1, 12) = "MATERIAL"
    Wbook.Sheets(1).Cells(1, 13) = "MASA"
    Wbook.Sheets(1).Cells(1, 14) = "ANCHO"
    Wbook.Sheets(1).Cells(1, 15) = "LARGO"
    Wbook.Sheets(1).Cells(1, 16) = "ESPESOR"
    Wbook.Sheets(1).Cells(1, 17) = "ING. FABRICACIÓN"
    Wbook.Sheets(1).Cells(1, 18) = "REV. PLANOS"
    Wbook.Sheets(1).Cells(1, 19) = "ING. SISTEMAS"
    Wbook.Sheets(1).Cells(1, 20) = "VER. ESTRUCTURAL"
    Wbook.Sheets(1).Cells(1, 21) = "APROBADOR"

'CONTADOR COMPLEJO
'=================
    'CANTIDAD
    For i = 1 To N_ITEM
        CANTIDAD_PN = 0
        For j = 1 To N_ITEM
            If PN_PROP(i, 1) = PN_PROP(j, 1) Then
                CANTIDAD_PN = CANTIDAD_PN + 1
                For k = 1 To 21
                    PN_DEPUR(i, k) = PN_PROP(i, k)
                Next
            End If
        Next
        PN_DEPUR(i, 4) = CANTIDAD_PN
    Next

    'SE BORRAN ITEMS REPETIDOS
    For i = 1 To N_ITEM
        For j = 1 To i
            If i <> j Then
                If PN_DEPUR(i, 1) = PN_DEPUR(j, 1) Then
                    For k = 1 To 21
                        PN_DEPUR(i, k) = ""
                    Next
                End If
            End If
        Next
    Next

    'SE ELIMINAN ESPACIOS EN BLANCO
    N_DEPUR = 0
    DIF_BOOL = False
    For i = 1 To N_ITEM
        If PN_DEPUR(i, 1) = "" Then 'ENCUENTRA UN ESPACIO LIBRE
            If DIF_BOOL = False Then 'SE CUENTA DESDE DONDE COMPIENZAN LOS ESPACIOS VACÍOS (SIENTO QUE ME ESTOY RASCANDO LA OREJA IZQUIERDA CON LA MANO DERECHA)
                DIF_N_DEPUR = i - 1
                DIF_BOOL = True
            End If
            NO_NULO = False
            For j = i + 1 To N_ITEM
                If PN_DEPUR(j, 1) <> "" And NO_NULO = False Then 'ENCUENTRA UN VALOR NO NULO, SI YA ENTRO LO EVITA
                    NO_NULO = True
                    N_DEPUR = N_DEPUR + 1
                    For k = 1 To 21 'TRANSFIERE TODOS LOS VALORES AL ESPACIO LIBRE
                        PN_DEPUR(i, k) = PN_DEPUR(j, k)
                    Next
                    For k = 1 To 21 'BORRA EL VALOR NO NULO
                        PN_DEPUR(j, k) = ""
                    Next
                End If
            Next
        End If
    Next
    
    N_ITEM = DIF_N_DEPUR + N_DEPUR

    For i = 1 To N_ITEM
        Wbook.Sheets(1).Cells(i + 2, 2) = PN_DEPUR(i, 20)
        For j = 1 To 19
            Wbook.Sheets(1).Cells(i + 2, j + 2) = PN_DEPUR(i, j)
        Next
    Next

'CONTADOR SIMPLE
'===============
'    For i = 1 To N_ITEM
'        Wbook.Sheets(1).cells(i + 2, 2) = PN_PROP(i, 20)
'        For j = 1 To 19
'            Wbook.Sheets(1).cells(i + 2, j + 2) = PN_PROP(i, j)
'        Next
'    Next
    
    Wbook.Sheets(1).Cells(N_ITEM + 4, 2) = "[1] ANTES DE CREAR NUEVOS DOCUMENTOS, VERIFICAR SI YA EXISTEN (ELIMINARLOS PUEDE RESULTAR PROBLEMATICO)"
    Wbook.Sheets(1).Cells(N_ITEM + 5, 2) = "[2] CARGAR UN PLANO ZG PARA LA NOMENCLATURA GENERADA. "
    Wbook.Sheets(1).Cells(N_ITEM + 6, 2) = "[3] CARGAR UN ARCHIVO DD3 POR CADA PART NUMBER FADEA QUE TERMINE EN -0XX"
    Wbook.Sheets(1).Cells(N_ITEM + 7, 2) = "[4] CARGAR UN ARCHIVO PD3 POR CADA PART NUMBER FADEA QUE TERMINE EN -0XX, A MENOS QUE ESTE SEA UNA SIMETRÍA"
    Wbook.Sheets(1).Cells(N_ITEM + 8, 2) = "[5] CARGAR DATOS BASICOS DE INGENIERÍA"
    Wbook.Sheets(1).Cells(N_ITEM + 9, 2) = "[6] CARGAR NOTA DE MODIFICACIÓN [NDM]"
    Wbook.Sheets(1).Cells(N_ITEM + 10, 2) = "[7] CARGAR PROPUESTA DE MODIFICACIÓN [PDM]"
    
    '======================================================================
Call Rutas("PDT", RUTA_SALIDA, PROY_CODE)

DESCAUX = Split(PN_COMPLETO, "_")
PN = DESCAUX(0)
DESC = DESCAUX(1)

If Dir(UCase(RUTA_SALIDA & UCase(PN) & "\"), vbDirectory) = "" Then
    MkDir (UCase(RUTA_SALIDA & UCase(PN) & "\"))
End If

Ruta_STEX = RUTA_SALIDA & UCase(PN) & "\ST-" & PN

ExcelLate.Workbooks(1).SaveAs FileName:=Ruta_STEX
ExcelLate.Workbooks(1).Close SaveChanges:=False

End Sub

Sub GetNextNode(oCurrentProduct As Product, NODO, PN_PROP, N_ITEM, N_PROD)

    N_PROD = N_PROD + 1
    Dim oCurrentTreeNode As Product
    Dim i As Integer
    
    NODO = NODO + 1

    'Loop through every tree node for the current product
    For i = 1 To oCurrentProduct.Products.Count
    
        'MsgBox N_ITEM
    
        Set oCurrentTreeNode = oCurrentProduct.Products.ITEM(i)
    
    
        Cantidad = 0
        YA_TA = False
'        For k = 1 To oCurrentProduct.Products.Count
'            If oCurrentTreeNode.PartNumber = oCurrentProduct.Products.ITEM(k).PartNumber Then
'                CANTIDAD = CANTIDAD + 1
'            End If
'            If PN_PROP(k, 1) = oCurrentTreeNode.PartNumber Then
'            YA_TA = True
'            End If
'        Next
        
        'VERIFICA SI EL PN ES DE FADEA
        PN_FADEA = False
        If InStr(1, oCurrentTreeNode.PartNumber, "F5-C-", vbTextCompare) <> 0 Then
            PN_FADEA = True
        End If
        
        'VERIFICA SI EL PN ES UN ESTÁNDARD
        GRUP_ESTANDARES = False
        If InStr(1, oCurrentTreeNode.PartNumber, "STANDAR", vbTextCompare) <> 0 Then
            GRUP_ESTANDARES = True
        End If
        
        'MsgBox oCurrentTreeNode.PartNumber & " CANTIDAD:" & CANTIDAD
        If GRUP_ESTANDARES = False Then
        
            If YA_TA = False Then
            
                N_ITEM = N_ITEM + 1
                PN_PROP(N_ITEM, 1) = oCurrentTreeNode.PartNumber
                PN_PROP(N_ITEM, 2) = oCurrentTreeNode.Name
                
                ' Determine if the current node is a part, product or component
                If IsPart(oCurrentTreeNode) = True Then
                    On Error GoTo LABELERROR
                    PN_PROP(N_ITEM, 3) = oCurrentTreeNode.Parameters.ITEM("Nivel").ValueAsString
                    PN_PROP(N_ITEM, 4) = Cantidad
                    PN_PROP(N_ITEM, 5) = oCurrentTreeNode.Parameters.ITEM("Numero_Parte").ValueAsString
                    PN_PROP(N_ITEM, 6) = oCurrentTreeNode.Parameters.ITEM("Nro_Ord").ValueAsString
                    PN_PROP(N_ITEM, 7) = oCurrentTreeNode.Parameters.ITEM("Autor").ValueAsString
                    PN_PROP(N_ITEM, 8) = oCurrentTreeNode.Parameters.ITEM("Estado").ValueAsString
                    PN_PROP(N_ITEM, 9) = oCurrentTreeNode.Parameters.ITEM("Tipo").ValueAsString
                    PN_PROP(N_ITEM, 10) = oCurrentTreeNode.Parameters.ITEM("Material").ValueAsString
                    PN_PROP(N_ITEM, 11) = oCurrentTreeNode.Parameters.ITEM("Masa").ValueAsString
                    PN_PROP(N_ITEM, 12) = oCurrentTreeNode.Parameters.ITEM("Ancho").ValueAsString
                    PN_PROP(N_ITEM, 13) = oCurrentTreeNode.Parameters.ITEM("Largo").ValueAsString
                    PN_PROP(N_ITEM, 14) = oCurrentTreeNode.Parameters.ITEM("Espesor").ValueAsString
                    PN_PROP(N_ITEM, 15) = oCurrentTreeNode.Parameters.ITEM("ING. FABRIC.").ValueAsString
                    PN_PROP(N_ITEM, 16) = oCurrentTreeNode.Parameters.ITEM("REVISÓ").ValueAsString
                    PN_PROP(N_ITEM, 17) = oCurrentTreeNode.Parameters.ITEM("ING. SISTEMAS").ValueAsString
                    PN_PROP(N_ITEM, 18) = oCurrentTreeNode.Parameters.ITEM("VER. RESIST.").ValueAsString
                    PN_PROP(N_ITEM, 19) = oCurrentTreeNode.Parameters.ITEM("APROBÓ").ValueAsString
                    PN_PROP(N_ITEM, 20) = NODO
                    
                ElseIf IsProduct(oCurrentTreeNode) = True Then
                    On Error Resume Next
                    PN_PROP(N_ITEM, 3) = oCurrentTreeNode.Parameters.RootParameterSet.DirectParameters.ITEM("Nivel").ValueAsString
                    PN_PROP(N_ITEM, 4) = Cantidad
                    PN_PROP(N_ITEM, 5) = oCurrentTreeNode.Parameters.RootParameterSet.DirectParameters.ITEM("Numero_Parte").ValueAsString
                    PN_PROP(N_ITEM, 6) = oCurrentTreeNode.Parameters.RootParameterSet.DirectParameters.ITEM("Nro_Ord").ValueAsString
                    PN_PROP(N_ITEM, 7) = oCurrentTreeNode.Parameters.RootParameterSet.DirectParameters.ITEM("Autor").ValueAsString
                    PN_PROP(N_ITEM, 8) = oCurrentTreeNode.Parameters.RootParameterSet.DirectParameters.ITEM("Estado").ValueAsString
                    PN_PROP(N_ITEM, 9) = oCurrentTreeNode.Parameters.RootParameterSet.DirectParameters.ITEM("Tipo").ValueAsString
                    PN_PROP(N_ITEM, 10) = oCurrentTreeNode.Parameters.RootParameterSet.DirectParameters.ITEM("Material").ValueAsString
                    PN_PROP(N_ITEM, 11) = oCurrentTreeNode.Parameters.RootParameterSet.DirectParameters.ITEM("Masa").ValueAsString
                    PN_PROP(N_ITEM, 12) = oCurrentTreeNode.Parameters.RootParameterSet.DirectParameters.ITEM("Ancho").ValueAsString
                    PN_PROP(N_ITEM, 13) = oCurrentTreeNode.Parameters.RootParameterSet.DirectParameters.ITEM("Largo").ValueAsString
                    PN_PROP(N_ITEM, 14) = oCurrentTreeNode.Parameters.RootParameterSet.DirectParameters.ITEM("Espesor").ValueAsString
                    PN_PROP(N_ITEM, 15) = oCurrentTreeNode.Parameters.RootParameterSet.DirectParameters.ITEM("ING. FABRIC.").ValueAsString
                    PN_PROP(N_ITEM, 16) = oCurrentTreeNode.Parameters.RootParameterSet.DirectParameters.ITEM("REVISÓ").ValueAsString
                    PN_PROP(N_ITEM, 17) = oCurrentTreeNode.Parameters.RootParameterSet.DirectParameters.ITEM("ING. SISTEMAS").ValueAsString
                    PN_PROP(N_ITEM, 18) = oCurrentTreeNode.Parameters.RootParameterSet.DirectParameters.ITEM("VER. RESIST.").ValueAsString
                    PN_PROP(N_ITEM, 19) = oCurrentTreeNode.Parameters.RootParameterSet.DirectParameters.ITEM("APROBÓ").ValueAsString
                    PN_PROP(N_ITEM, 20) = NODO
                    On Error GoTo 0
                    
                ElseIf IsProduct(oCurrentTreeNode) = False And IsPart(oCurrentTreeNode) = False Then
                    PN_PROP(N_ITEM, 20) = NODO
                
                End If
        
LABELERROR:
                    'MsgBox "P/N: " & oCurrentTreeNode.PartNumber & vbNewLine
                    If PN_FADEA = True Or Cantidad > 1 Then 'si el PN está mas de una vez significa que es un estándar contable, tambien cuenta si es un PN fadea.
                        PN_PROP(N_ITEM, 4) = Cantidad
                    ElseIf Cantidad = 1 Then
                        PN_PROP(N_ITEM, 4) = -1
                    End If
                    PN_PROP(N_ITEM, 20) = NODO
                    On Error GoTo -1
        
            End If
               
        ElseIf GRUP_ESTANDARES = True Then
    
            If oCurrentTreeNode.Products.Count > 0 Then
                'NODO = NODO + 1
                Call GetNextNode(oCurrentTreeNode, NODO, PN_PROP, N_ITEM, N_PROD)
                NODO = NODO - 1
            End If
    
        End If

   Next

End Sub

Function IsPart(objCurrentProduct As Product) As Boolean

    'Dim oTestPart As PartDocument
     On Error Resume Next
        
        If Right(objCurrentProduct.ReferenceProduct.Parent.Name, 8) = ".CATPart" Then
            IsPart = True
        Else
            IsPart = False
        End If
    On Error GoTo 0
       
End Function

Function IsProduct(objCurrentProduct As Product) As Boolean

    'Dim oTestProduct As ProductDocument
   
    On Error Resume Next
     
        If Right(objCurrentProduct.ReferenceProduct.Parent.Name, 11) = ".CATProduct" Then
            IsProduct = True
        Else
            IsProduct = False
        End If
        
    On Error GoTo 0
        
End Function

Attribute VB_Name = "A99_Rutas"
'AUTOR: SEBASTIAN ASSAIN
'NOMBRE: A99_RUTAS F50
'VERSION 1.0
'FECHA: 11/03/2022
'CAMBIOS:
'FRASE: NO PUEDES COMETER 2 VECES EL MISMO ERROR, LA SEGUNDA VEZ SERÁ POR ELECCIÓN
'DESCRIPCIÓN:   SE INGRESA CON UN TIPO (PROCESO, LIBERAR, PDT, CONGELAR) Y DEVUELVE UNA RUTA EN STRING

Sub Rutas(TIPO, RUTA_SALIDA, PROY_CODE)

Dim Rutas_Proyecto(1 To 150, 1 To 20) As Variant
Dim fsDataFile As Object
Dim sText As Object
Dim sPath As String
Dim sFullLine As String

Set fsDataFile = CreateObject("Scripting.FileSystemObject")

linea = 0
'The fully qualified path to your lookup file
sPath = "\\srie04in1\Settings_Catia\FADEASA_CATIA\Central_EnvR27\Catalogos\ARCHIVOS_DE_ARRANQUE\PROYECTO\Rutas.csv"

'Create a text stream from your FileSystemObject
Set sText = fsDataFile.OpenTextFile(sPath, 1, False)

'Loop through each line in the text stream
Do While sText.AtEndOfStream <> True
    linea = linea + 1
    sFullLine = sText.ReadLine
    Count = Len(sFullLine) - Len(Replace(sFullLine, ";", ""))
    saCsvData = Split(sFullLine, ";")
    For i = 1 To Count + 1
        Rutas_Proyecto(linea, i) = saCsvData(i - 1)
    Next
Loop

For j = 2 To 15
    If Rutas_Proyecto(2, j) = PROY_CODE Then
        For i = 1 To 38
            If Rutas_Proyecto(i, 1) = TIPO Then
                RUTA_SALIDA = Rutas_Proyecto(i, j)
            End If
        Next
    End If
Next

'Si se está haciendo un back up de la estructura de producto se lo hace de esta manera
If TIPO = "BACKUP" Then
    RUTA_SALIDA = RUTA_SALIDA & Year(Date) & Month(Date) & Day(Date) & Hour(Now) & "-" & UCase(Environ("username")) & "_desdeCATIA_No-Prioritario_F50_Estructura de Producto.xlsm"
End If

sText.Close

End Sub

Attribute VB_Name = "A99_Unidades"
Sub SetearUnidades()

Dim oSettingControllers As SettingControllers
Set oSettingControllers = CATIA.SettingControllers
 
Dim oUnitsSheetSettingAtt As SettingController
Set oUnitsSheetSettingAtt = oSettingControllers.ITEM("CATLieUnitsSheetSettingCtrl")

Dim oMagnitude As String
Dim oUnit As String

Dim oGetDecimal As Double
Dim oGetExpo As Double

Dim oUnitInch As String

oMagnitude = "AREA"
oUnit = ""

oUnitsSheetSettingAtt.GetMagnitudeValues oMagnitude, oUnit, oGetDecimal, oGetExpo

If (oUnit <> "Square meter") Then

    oUnitInch = "Square meter"
    oUnitsSheetSettingAtt.SetMagnitudeValues oMagnitude, oUnitInch, 6#, 3#

    oUnitsSheetSettingAtt.SaveRepositoryForUnits
    oUnitsSheetSettingAtt.CommitForUnits
    oUnitsSheetSettingAtt.Commit

End If

oMagnitude = "MASS"
oUnit = ""
 
oUnitsSheetSettingAtt.GetMagnitudeValues oMagnitude, oUnit, oGetDecimal, oGetExpo


If (oUnit <> "Gram") Then

    oUnitInch = "Gram"
    oUnitsSheetSettingAtt.SetMagnitudeValues oMagnitude, oUnitInch, 6#, 3#
    
    oUnitsSheetSettingAtt.SaveRepositoryForUnits
    oUnitsSheetSettingAtt.CommitForUnits
    oUnitsSheetSettingAtt.Commit

End If

oMagnitude = "VOLUME"
oUnit = ""

oUnitsSheetSettingAtt.GetMagnitudeValues oMagnitude, oUnit, oGetDecimal, oGetExpo

If (oUnit <> "Cubic centimeter") Then

    oUnitInch = "Cubic centimeter"
    oUnitsSheetSettingAtt.SetMagnitudeValues oMagnitude, oUnitInch, 6#, 3#

    oUnitsSheetSettingAtt.SaveRepositoryForUnits
    oUnitsSheetSettingAtt.CommitForUnits
    oUnitsSheetSettingAtt.Commit

End If

oMagnitude = "LENGTH"
oUnit = ""

oUnitsSheetSettingAtt.GetMagnitudeValues oMagnitude, oUnit, oGetDecimal, oGetExpo

If (oUnit <> "Milimeter") Then

    oUnitInch = "Milimeter"
    oUnitsSheetSettingAtt.SetMagnitudeValues oMagnitude, oUnitInch, 6#, 3#

    oUnitsSheetSettingAtt.SaveRepositoryForUnits
    oUnitsSheetSettingAtt.CommitForUnits
    oUnitsSheetSettingAtt.Commit

End If


End Sub

Attribute VB_Name = "A99_Usuarios"
'AUTOR: SEBASTIAN ASSAIN
'NOMBRE: A99_Usuarios
'VERSION 1.0
'FECHA: 04/04/2022
'CAMBIOS: ---
'DESCRIPCIÓN: SE INGRESA EL CODIGO DEL PROYECTO Y LA SUBRUTINA ENTREGA UNA MATRIZ CON USUARIOS, NUMEROS DE CONTROL, ÁREA PERTENECIENTE Y PERFIL

Sub Usuarios(ByRef ARR_USUARIOS() As Variant)

Dim Matriz_Us(1 To 150, 1 To 20) As Variant
ReDim ARR_USUARIOS(1 To 40, 1 To 4) As Variant
Dim fsDataFile As Object
Dim sText As Object
Dim sPath As String
Dim sFullLine As String

Call PROYECTO(PROY_CODE, PROYS, ARM_SYS)

Set fsDataFile = CreateObject("Scripting.FileSystemObject")

linea = 0
'The fully qualified path to your lookup file
sPath = "\\srie04in1\Settings_Catia\FADEASA_CATIA\Central_EnvR27\Catalogos\ARCHIVOS_DE_ARRANQUE\PROYECTO\Rutas.csv"

'Create a text stream from your FileSystemObject
Set sText = fsDataFile.OpenTextFile(sPath, 1, False)

'Loop through each line in the text stream
Do While sText.AtEndOfStream <> True
    linea = linea + 1
    sFullLine = sText.ReadLine
    Count = Len(sFullLine) - Len(Replace(sFullLine, ";", ""))
    saCsvData = Split(sFullLine, ";")
    For i = 1 To Count + 1
        Matriz_Us(linea, i) = saCsvData(i - 1)
    Next
Loop

For j = 1 To 15
    If Matriz_Us(2, j) = PROY_CODE Then
        it = 0
        For i = 41 To 80
            If InStr(1, Matriz_Us(i, j), "|") <> 0 Then
                it = it + 1
                aux_usr = Split(Matriz_Us(i, j), "|")
                ARR_USUARIOS(it, 1) = aux_usr(0)
                ARR_USUARIOS(it, 2) = aux_usr(1)
                ARR_USUARIOS(it, 3) = aux_usr(2)
                ARR_USUARIOS(it, 4) = aux_usr(3)
                'Debug.Print ARR_USUARIOS(it, 4)
            End If
        Next
    End If
Next

sText.Close

End Sub

Attribute VB_Name = "A99_ZBUFFER"
Sub CATMain()

Set mySettingControllers = CATIA.SettingControllers

Set MyVisSetting = mySettingControllers.ITEM("CATVizVisualizationSettingCtrl")

'MsgBox MyVisSetting.AllZBufferElementMode

If MyVisSetting.AllZBufferElementMode Then
    MyVisSetting.AllZBufferElementMode = False
Else
    MyVisSetting.AllZBufferElementMode = True
End If

'MyVisSetting.AntiAliasingOffset = 0.1
'
'MyVisSetting.FullSceneAntiAliasingMode = CATFSAAMode_8xSuperSampling
'
'MyVisSetting.SaveRepository
'
'Set myWindow = CATIA.ActiveWindow
'
'Set myNewWindow = myWindow.NewWindow()
'
'myWindow.Close

End Sub

Attribute VB_Name = "A9_Liberar_PN"
'AUTOR: SEBASTIAN ASSAIN
'NOMBRE: A9_LIBERAR_PN
'VERSION 2.0
'FECHA: 11/11/2021
'CAMBIOS: SE ADMITE LA LIBERACION DE DOCUMENTOS DE FABRICACIÓN [DF]
'FRASE: NINGUN MAR EN CALMA HIZO EXPERTO A UN MARINERO
'DESCRIPCIÓN: LIBERA P/N DEL PROYECTO F50
Public DF As Variant
Public ARR_PN_NO_LIBERADO(1 To 1000) As String

Sub CATMain()
'CATIA.DisplayFileAlerts = False
'DrawingDocument

Dim Archivo_Existente As Variant
Dim Ruta As String
Dim RUTA_SALIDA As String
Dim Nombre_Ruta As String
Dim Nombre_Ruta_Archivo_Guardado As String
Dim Nombre_Archivo As String
Dim Reemplazo As VbMsgBoxResult
Dim Armonizado As VbMsgBoxResult
Dim Tipo_Archivo As String
Dim Nom_PartProd As String
Dim producto As Product
Dim relationsproducto1 As Relations
Dim productDocument1 As ProductDocument
Dim product1 As Product
Dim partDocument1 As PartDocument
Dim part1 As Part
Dim relationsparte1 As Relations
Dim oseleccion As Selection
Dim Instancia As String
Dim Instancia_sp As String
Dim NInst As Variant
Dim NInst_Nueva As Variant
Dim retro As Integer
Dim BuscaPunto As String
Dim InstVec() As Variant
Dim NInstVec() As Variant
Dim Cambio As Boolean
Dim BodyToRename As Body
Dim strParam1 As StrParam
Dim parameters1 As Parameters
Dim Param As Parameter
Dim publications1 As Publications


If UCase(Environ("username")) = "USUARIO" Or UCase(Environ("username")) = "NUNES" Or UCase(Environ("username")) = "TOSELLI" _
Or UCase(Environ("username")) = "CAMAYO" Or UCase(Environ("username")) = "ASSAIN" Or UCase(Environ("username")) = "DIAZR" _
Or UCase(Environ("username")) = "PACCIORETTI" Then

    'SI NO EXISTE NINGUN DOCUMENTO ABIERTO SE EVITA QUE LA MACRO DEVUELVA UN ERROR
    '=============================================================================
    If CATIA.Documents.Count = 0 Or CATIA.Windows.Count = 0 Then
        MsgBox "Debe tener abierto al menos un documento para utilizar esta herramienta", vbCritical
        Exit Sub
    End If
    
    Call PROYECTO(PROY_CODE, PROYS, ARM_SYS)
    
    'NUMEROS ENTEROS PARA TRABAJAR CON PART NUMBERS
    '==============================================
    Call Param_PN(ARR_PN, PROY_CODE)
    intgr_N_PN = ARR_PN(1)
    '==============================================
    
    Set oseleccion = CATIA.ActiveDocument.Selection
    'MsgBox oSeleccion.Count
    
    '//////////////////////////////////////////////////////////////////////////////////////////////////////////////////////////////////////////////////////////////////
    'SI ES UN ARCHIVO PRODUCTO (AGRUPA PARTES Y PRODUCTOS)
    '/////////////////////////////////////////////////////////////////////////////////////////////////////////////////////////////////////////////////////////////
    If oseleccion.Count > 1 Then
    
        MsgBox "Sólo se puede liberar de a un número de parte a la vez.", vbCritical, "Alcance de macro acotado."
        Exit Sub
    
    ElseIf oseleccion.Count = 1 Then
    
        On Error Resume Next
        If oseleccion.ITEM(1).Value.ReferenceProduct.Parent.Product.Name = CATIA.ActiveDocument.Product.Name Then
            MsgBox "Para evitar problemas de pérdidas de archivos esta prohibido LIBERAR productos o partes sin abrir su conjunto inmediato superior." & _
            vbNewLine & vbNewLine & "Abra el conjunto inmediato superior y vuelva a intentarlo desde allí.", vbCritical, "Debe abrir el CSI para continuar."
            Exit Sub
        End If
        On Error GoTo 0
        
        'SI EL ARCHIVO COMIENZA POR DD3 O DF SIGNIFICA QUE YA SE HA LIBERADO
        '===================================================================
        If Left(oseleccion.ITEM(1).Value.ReferenceProduct.Parent.Name, 3) = "DD3" Or Left(oseleccion.ITEM(1).Value.ReferenceProduct.Parent.Name, 2) = "DF" Then
            MsgBox "No se puede liberar un archivo ya liberado!" & vbCrLf & vbCrLf & "Considere hacer una REVISIÓN", vbCritical, "Archivo: " & oseleccion.ITEM(1).Value.ReferenceProduct.Parent.Name
            Exit Sub
        End If
        
        UserForm2.Show
        
        If DF = -1 Then
            MsgBox "El archivo NO fue liberado.", vbCritical, "Liberacion! "
            Exit Sub
        End If
        
        'SI SOLAMENTE TENEMOS ABIERTA UNA PARTE, NO HACE FALTA PASAR A MODO DISEŃO
        '=========================================================================
        If TypeName(CATIA.ActiveDocument) <> "PartDocument" Then
            CATIA.ActiveDocument.Product.ApplyWorkMode DESIGN_MODE
        End If
            
        'EN EL PROYECTO F50 LA RUTA ES LA MISMA, PERO SE DEJA LA OPCIÓN DE CAMBIARLA
        '===========================================================================
        If DF = 1 Then
            TIPO = "DF"
        Else
            TIPO = "DD3"
        End If
        
        Call Rutas(TIPO, RUTA_SALIDA, PROY_CODE)
        
        'LOOP DESDE 1 HASTA LOS ELEMENTOS SELECCIONADOS
        '==============================================
        For i = 1 To oseleccion.Count
        
            'SI EL TIPO DE DOCUMENTO ES UN PRODUCTO
            '======================================
            If TypeName(oseleccion.ITEM(i).Value) = "Product" Then

                '======================================================================================================================================================
                'SI EL DOCUMENTO GUARDADO ES UNA PARTE
                '======================================================================================================================================================
                If TypeName(oseleccion.ITEM(i).Value.ReferenceProduct.Parent) = "PartDocument" Then
                
                    Set part1 = oseleccion.ITEM(i).Value.ReferenceProduct.Parent.Part
                    Set relationsparte1 = part1.Relations
                    Set BodyToRename = oseleccion.ITEM(i).Value.ReferenceProduct.Parent.Part.Bodies.ITEM(1)
                    Set parameters1 = part1.Parameters

                    PNAUX = Split(oseleccion.ITEM(i).Value.ReferenceProduct.Parent.Part.Name, "_")
                    PN = PNAUX(0)
                    
                    PNPB = Left(oseleccion.ITEM(i).Value.ReferenceProduct.Parent.Part.Name, intgr_N_PN)
                    Ruta = RUTA_SALIDA

                    Call REV_PN(Ruta, PNPB, TIPO, REV, N_DF, "PARTE")
                    
                    Call Param_Check(REV)
                    
                    If DF <> 1 Then
                        Archivo_Previo = Ruta & TIPO & "-" & PNPB & "-"
                    Else
                        Archivo_Previo = Ruta & TIPO & N_DF & "-" & PNPB & "-"
                    End If
                    
                    'SI SE LIBERA COMO 'DOCUMENTO DE FABRICACIÓN' SE OMITE CHEQUEAR PARÁMETROS YA QUE SE ASUME NECESARIA CIERTA AGILIDAD EXTRA.
                    '==========================================================================================================================
                    If DF <> 1 And NO_LIBERA = True Then
                        MsgBox "La parte esta incompleta, complete los parámetros necesarios y vuelva a intentarlo.", vbCritical, "Parámetros incompletos"
                        Exit Sub
                    End If 'DF <> 1
                    
                    'SE OBTIENE EL NOMBRE Y LA RUTA DEL ARCHIVO MODIFICABLE, GENERALMENTE UBICADO EN UN SERVIDOR DE INGENIERÍA
                    '=========================================================================================================
                    Ruta_Inicial = oseleccion.ITEM(i).Value.ReferenceProduct.Parent.FullName
                    Nombre_Inicial = oseleccion.ITEM(i).Value.ReferenceProduct.Parent.Name
                    
                    'SE OBTIENE EL NOMBRE Y LA RUTA DEL ARCHIVO MODIFICABLE, GENERALMENTE UBICADO EN UN SERVIDOR DE INGENIERÍA
                    '=========================================================================================================
                    Nombre_Liberado = Archivo_Previo & REV & ".CATPart"
                    
                    TIPO_AUX = TIPO & N_DF

                    'SE ADVIERTE QUE EL ARCHIVO SE VA A LIBERAR
                    '==========================================
                    Liberacion = MsgBox("Usted está por liberar el P/N: " & TIPO_AUX & "-" & PNPB & "-" & REV & _
                    vbCrLf & vbCrLf & "(1)El archivo será propiedad del Área de Documentacion Técnica" & vbCrLf & vbCrLf & "(2)Usted no podrá modificarlo" _
                    , vbOKCancel + vbCritical, "Atención!" & part1.Name)
                    If Liberacion = vbOK Then
                        
                        On Error Resume Next
                        Err.Clear
                        CATIA.StartCommand ("Clear History")
                        oseleccion.ITEM(i).Value.ReferenceProduct.Parent.SaveAs (Nombre_Liberado)
                        
                        'SE GUARDA EL CONJUNTO INMEDIATO SUPERIOR
                        '========================================
                        CATIA.ActiveDocument.Selection.ITEM(1).LeafProduct.Parent.Parent.ReferenceProduct.Parent.Save
                        
                        'SI HAY UN ERROR EN EL GUARDADO EVITA BORRAR EL ARCHIVO ORIGINAL
                        '================================================================
                        Mata = True
                        If Err.Number <> 0 Then
                            Mata = False
                        End If
                        If Mata = True Then
                            Kill (Ruta_Inicial)
                        Else
                            MsgBox "La parte no ha podido liberarse debido a que usted no ha aceptado las condiciones de la ventana previa." _
                            & vbNewLine & vbNewLine & "Vuelva a intentarlo.", vbCritical
                            Exit Sub
                        End If
                        On Error GoTo 0
                        
                    ElseIf Liberacion = vbCancel Then
                        MsgBox "El archivo NO fue liberado", vbCritical, "Liberacion! " & part1.Name
                        Exit Sub
                    End If
                    
                '========================================================================================================================================================
                'SI EL DOCUMENTO GUARDADO ES UN PRODUCTO
                '========================================================================================================================================================
                ElseIf TypeName(oseleccion.ITEM(i).Value.ReferenceProduct.Parent) = "ProductDocument" Then
                    
                    Set product1 = oseleccion.ITEM(i).Value.ReferenceProduct.Parent.Product

                    PNAUX = Split(oseleccion.ITEM(i).Value.ReferenceProduct.Parent.Product.Name, "_")
                    PN = PNAUX(0)
                    
                    PNPB = Left(oseleccion.ITEM(i).Value.ReferenceProduct.Parent.Product.Name, intgr_N_PN)
                    Ruta = RUTA_SALIDA
                    
                    PartProd = "PRODUCTO"
                    Call REV_PN(Ruta, PNPB, TIPO, REV, N_DF, PartProd)

                    Call Param_Check(REV)
                    
                    If DF <> 1 Then
                        Archivo_Previo = Ruta & TIPO & "-" & PNPB & "-"
                    Else
                        Archivo_Previo = Ruta & TIPO & N_DF & "-" & PNPB & "-"
                    End If
                    
                    Call Rutas(TIPO, RUTA_SALIDA, PROY_CODE)
                    
                    'SI SE LIBERA COMO 'DOCUMENTO DE FABRICACIÓN' SE OMITE CHEQUEAR PARÁMETROS YA QUE SE ASUME NECESARIA CIERTA AGILIDAD EXTRA.
                    '==========================================================================================================================
                    If DF <> 1 And NO_LIBERA = True Then
                        MsgBox "La parte esta incompleta, complete los parámetros necesarios y vuelva a intentarlo.", vbCritical, "Parámetros incompletos"
                        Exit Sub
                    ElseIf DF = 1 And NO_LIBERA = True Then
                        NO_LIBERA = False
                    End If 'DF <> 1
                    
                    Call Liberados(ARR_PN_NO_LIBERADO, k_aux)
                    
                    If k_aux > 1 Then
                        Mensaje_Listado = "Los siguientes números de parte no se encuentran liberados:" & vbCrLf
                    ElseIf k_aux = 1 Then
                        Mensaje_Listado = "El siguiente número de parte no se encuentra liberado:" & vbCrLf
                    End If
                    
                    For h = 1 To k_aux
                        Mensaje_Listado = Mensaje_Listado & vbCrLf & ARR_PN_NO_LIBERADO(h)
                        If h = k_aux Then
                        Mensaje_Listado = Mensaje_Listado & vbCrLf & vbCrLf & "Debe liberarlos para continuar con la liberación del producto."
                        End If
                    Next
                    
                    If NO_LIBERA = True Then
                        MsgBox Mensaje_Listado, vbCritical, "Error de liberación."
                        Exit Sub
                    End If
                    
                    'SE OBTIENE EL NOMBRE Y LA RUTA DEL ARCHIVO MODIFICABLE, GENERALMENTE UBICADO EN UN SERVIDOR DE INGENIERÍA
                    '=========================================================================================================
                    Ruta_Inicial = oseleccion.ITEM(i).Value.ReferenceProduct.Parent.FullName
                    Nombre_Inicial = oseleccion.ITEM(i).Value.ReferenceProduct.Parent.Name
    
                    'SI EL ARCHIVO COMIENZA POR DD3 SIGNIFICA QUE YA SE HA LIBERADO
                    '==============================================================
                    If Left(Nombre_Inicial, 3) = "DD3" Or Left(Nombre_Inicial, 2) = "DF" Then
                        MsgBox "No se puede liberar un archivo ya liberado!" & vbCrLf & vbCrLf & "Considere hacer una REVISIÓN", vbCritical, "Archivo: " & Nombre_Inicial
                        Exit Sub
                    End If
                    
                    'SE OBTIENE EL NOMBRE Y LA RUTA DEL ARCHIVO MODIFICABLE, GENERALMENTE UBICADO EN UN SERVIDOR DE INGENIERÍA
                    '=========================================================================================================
                    Nombre_Liberado = Archivo_Previo & REV & ".CATProduct"
                    
                    TIPO_AUX = TIPO & N_DF

                    'SE ADVIERTE QUE EL ARCHIVO SE VA A LIBERAR
                    '==========================================
                    Liberacion = MsgBox("Usted está por liberar el P/N: " & TIPO_AUX & "-" & PNPB & "-" & REV & _
                    vbCrLf & vbCrLf & "(1)El archivo será propiedad del Área de Documentacion Técnica" & vbCrLf & vbCrLf & "(2)Usted no podrá modificarlo" _
                    , vbOKCancel + vbCritical, "Atención!" & product1.Name)
                    If Liberacion = vbOK Then
                        
                        On Error Resume Next
                        Err.Clear
                        CATIA.StartCommand ("Clear History")
                        oseleccion.ITEM(i).Value.ReferenceProduct.Parent.SaveAs (Nombre_Liberado)
                        
                        'SE GUARDA EL CONJUNTO INMEDIATO SUPERIOR
                        '========================================
                        CATIA.ActiveDocument.Selection.ITEM(1).LeafProduct.Parent.Parent.ReferenceProduct.Parent.Save
                        
                        'SI HAY UN ERROR EN EL GUARDADO EVITA BORRAR EL ARCHIVO ORIGINAL
                        '================================================================
                        Mata = True
                        If Err.Number <> 0 Then
                            Mata = False
                        End If
                        If Mata = True Then
                            Kill (Ruta_Inicial)
                        Else
                            MsgBox "La parte no ha podido liberarse debido a que usted no ha aceptado las condiciones de la ventana previa." _
                            & vbNewLine & vbNewLine & "Vuelva a intentarlo.", vbCritical
                            Exit Sub
                        End If
                        On Error GoTo 0
                        
                    ElseIf Liberacion = vbCancel Then
                        MsgBox "El archivo NO fue liberado", vbCritical, "Liberacion! " & product1.Name
                        Exit Sub
                    End If
                
                
                End If
            
            ElseIf TypeName(oseleccion.ITEM(i).Value) = "Part" Then
            
                MsgBox "Usted a selecionado una parte, debe seleccionar la instancia!" & vbCrLf & " El archivo NO se guardará", vbCritical, "Atencion!!"
            
            End If
        
        Next
    
    '///////////////////////////////////////////////////////////////////////////////////////////////////////////////////////////////////////
    'SI ES UN ARCHIVO INDIVIDUAL
    '///////////////////////////////////////////////////////////////////////////////////////////////////////////////////////////////////////
    Else  'SI NO HAY NADA SELECCIONADO
    
        'Se verifica el tipo de archivo que esta abierto
        Tipo_Archivo = TypeName(CATIA.ActiveDocument)
        '========================================SI EL ARCHIVO ES UN PRODUCTO===============================================================
        '===================================================================================================================================
        If Tipo_Archivo = "ProductDocument" And oseleccion.Count = 0 Then
            
            MsgBox "Seleccione al menos una parte o un producto para liberar.", vbCritical
            Exit Sub
        
        '========================================SI EL ARCHIVO ES UNA PARTE=================================================================
        '===================================================================================================================================
        ElseIf Tipo_Archivo = "PartDocument" Then
        
            '===============SE RESTRINGE EL USO A PARTES CONTENIDAS EN PRODUCTOS============================================================
            MsgBox "Debe ejecutar esta acción desde el producto que contiene esta parte." & vbNewLine & vbNewLine _
            & "Recuerde guardar el producto contenedor al finalizar.", vbExclamation
            Exit Sub
            '===============================================================================================================================
            
        Else
        
            MsgBox "Cosa eh mandinga!! aca pasa algo raro (el archivo no es ni CATPart ni CATProduct)"
        
        End If
        
        'MsgBox Archivo_Existente
        'MsgBox Nombre_Archivo
        'MsgBox part1.Name
    End If
    
    
Else 'USUARIOS
    
    MsgBox "Usted no está registrado para liberar documentación.", vbCritical, "Atención! Sr. " & Environ("username")
    
End If 'USUARIOS
    
End Sub
Public Function ParameterExist(ByRef ParameterCollection As Parameters, ByVal ParameterName As String, ByRef OutputParameter As Parameter) As Boolean
    On Error Resume Next
    Err.Clear
    Set OutputParameter = ParameterCollection.ITEM(ParameterName)
    If Err.Number = 0 Then
        ParameterExist = True
    Else
        ParameterExist = False
    End If
End Function

Attribute VB_Name = "Barra_Progreso"
Sub Barra_Progreso(i, total)

UserForm8.Show modeless

End Sub

Attribute VB_Name = "Extraer_Plegados"
Const libro As String = "Plegado.xlsx"
Const Ruta As String = "C:\Users\assain\Desktop\"
Const hoja As String = "Plegado"
Dim xl As Object
Dim i As Long, j  As Long

Sub RadiosPlegado()
'Application.Visible = True
'Application.ScreenUpdating = False
'Application.DisplayAlerts = False
'Set xl = Workbooks.Open(ruta & libro)

Set xl = CreateObject("Excel.Application")
Datei = Ruta & libro
xl.Workbooks.Open FileName:=Datei
xl.Visible = True
xl.ActiveSheet.Activate

BorrarExcel Ruta, libro, hoja
j = 1
i = 1
GetNextNode CATIA.ActiveDocument.Product
Set xl = Nothing
'Application.ScreenUpdating = True
'Application.DisplayAlerts = True
End Sub

Private Function GetNextNode(producto As Product)
Dim r As Double, t  As Double
Dim saltear As Boolean
Dim cosa, FILTRO
Dim NODO As Product
Dim PARTE As PartDocument
Dim p As Integer

FILTRO = Array("ARM", "MBD", "CCR", "PE", "MS", "NAS", "M8", "LIB")

For p = 1 To producto.Products.Count
    
    Set NODO = producto.Products.ITEM(p)
    
    saltear = False
    For Each cosa In FILTRO
        If InStr(NODO.Name, cosa) > 0 Then saltear = True
        Next
        
    If Not saltear Then
        r = RadioPlegado(NODO)
        t = EspesorChapa(NODO)
        ss = SurfacicFlange(NODO)
        
        'completa proxima fila en excel...
        i = i + 1
        CompletarExcel Ruta, libro, hoja, i, j, NODO.PartNumber
        CompletarExcel Ruta, libro, hoja, i, j + 1, r
        CompletarExcel Ruta, libro, hoja, i, j + 2, t
        CompletarExcel Ruta, libro, hoja, i, j + 3, ss
        
        'recorre todo el sub-producto...
        If NODO.Products.Count > 0 Then
            GetNextNode NODO
            End If
        End If
    Next
End Function

Private Sub CompletarExcel( _
    Ruta As String, _
    libro As String, _
    hoja As String, _
    fila As Long, _
    columna As Long, _
    dato)
'Dim xl As Workbook
'Set xl = Workbooks.Open(ruta & libro)
xl.Sheets(hoja).Cells(fila, columna) = dato
'xl.Close True
'Set xl = Nothing
End Sub

Private Sub BorrarExcel( _
    Ruta As String, _
    libro As String, _
    hoja As String)
'Dim xl As Workbook
'Set xl = Workbooks.Open(ruta & libro)
With xl.Sheets(hoja).Cells
    .Clear
    .Cells(1, 1) = "Part Number"
    .Cells(1, 2) = "Radio (mm)"
    .Cells(1, 3) = "Espesor (mm)"
    .Cells(1, 4) = "Pliegues"
    End With
'xl.Close True
'Set xl = Nothing
End Sub

'Function RadioPlegado(parte As PartDocument) As Double
Private Function RadioPlegado(PARTE As Product) As Double
Dim n As String
n = PARTE.ReferenceProduct.Name & _
"\Sheet Metal Parameter.1\Bend Radius"
'Set p2 = parte.GetItem("Sheet Metal Parameter.1")
'"390-15777-401 PRIMARY 1 ---\Sheet Metal Parameter.1\Bend Radius"
'RadioPlegado = parte.Part.Parameters.GetItem(n).Value
On Error Resume Next
RadioPlegado = PARTE.Parameters.GetItem(n).Value
End Function
'Function RadioPlegado(parte As PartDocument) As Double
Private Function SurfacicFlange(PARTE As Product) As Double
Dim n As String

On Error Resume Next

'cuenta surfacic flanges
For k = 1 To 5
ssAux = "Surfacic Flange." & k
n = Left(PARTE.ReferenceProduct.Name, 13) & "\" & ssAux & "\Edge Of Part length"
Err.Clear
ssAux2 = PARTE.Parameters.ITEM(n).Value
    If Err.Number = 0 Then
        kcount = kcount + 1
    Else

    End If
Next

'cuenta flanges
For k = 1 To 5
ssAux = "Flange." & k
n = Left(PARTE.ReferenceProduct.Name, 13) & "\" & ssAux & "\Length"
Err.Clear
ssAux2 = PARTE.Parameters.ITEM(n).Value
    If Err.Number = 0 Then
        kcount = kcount + 1
    Else

    End If
Next

'partDocument1.Part.Bodies.ITEM(1).Name
'Set p2 = parte.GetItem("Sheet Metal Parameter.1")
'"390-15777-401 PRIMARY 1 ---\Sheet Metal Parameter.1\Bend Radius"
'RadioPlegado = parte.Part.Parameters.GetItem(n).Value

SurfacicFlange = kcount
End Function

'Function EspesorChapa(parte As PartDocument) As Double
Private Function EspesorChapa(PARTE As Product) As Double
Dim p As SheetMetalParameters, n As String
n = PARTE.ReferenceProduct.Name & _
"\Sheet Metal Parameter.1\Thickness"
'Set p = parte.ReferenceProduct.Parameters.SheetMetalParameters
'EspesorChapa = p.GetThickness
On Error Resume Next
EspesorChapa = PARTE.Parameters.GetItem(n).Value
End Function

Private Function IsPart(producto As Product) As Boolean
Dim PARTE As PartDocument
Set PARTE = Nothing
On Error Resume Next
Set PARTE = CATIA.Documents.ITEM( _
producto.PartNumber & ".CATPart")
If Not PARTE Is Nothing Then
    IsPart = True
    Else
    IsPart = False
    End If
End Function

Attribute VB_Name = "Module1"
Sub tools()

PID = Shell("C:\Program Files\3D-Tool V14\3D-Tool.exe", vbNormalFocus)
CreateObject("Excel.Application").Wait (Now + TimeValue("00:00:05"))

SendKeys "%" & "a"

CreateObject("Excel.Application").Wait (Now + TimeValue("00:00:01"))

SendKeys "o"

CreateObject("Excel.Application").Wait (Now + TimeValue("00:00:01"))

SendKeys "C:\Users\assain\Desktop\DF-F5-C-201130-003_Fitting.CATPart"

SendKeys "{ENTER}"

CreateObject("Excel.Application").Wait (Now + TimeValue("00:00:01"))

SendKeys "{ENTER}"

End Sub

Attribute VB_Name = "Module2"
Sub CATMain()

Dim Matriz_PARAM(100, 50) As Variant
Dim Param_List(1 To 30, 1 To 2) As String
Dim fsDataFile As Object
Dim sText As Object
Dim sPath As String
Dim sFullLine As String

REV = "A"

'LECTURA DE LOS CÓDIGOS
Call PROYECTO(PROY_CODE, PROYS, ARM_SYS)

'Dim MAT_CODE(1000, 44) As Variant
Call Rutas("PARAMETROS", RUTA_SALIDA, PROY_CODE)

Set fsDataFile = CreateObject("Scripting.FileSystemObject")
'The fully qualified path to your lookup file
sPath = RUTA_SALIDA

'Create a text stream from your FileSystemObject
Set sText = fsDataFile.OpenTextFile(sPath, 1, False)

'Loop through each line in the text stream
j = 0
Do While sText.AtEndOfStream <> True
    linea = linea + 1
    sFullLine = sText.ReadLine
    saCsvData = Split(sFullLine, ";")
    
    j = j + 1
    For i = 0 To UBound(saCsvData)
        Matriz_PARAM(j, i) = saCsvData(i)
    Next
    
Loop

For i = 2 To 30
    
    If InStr(1, Matriz_PARAM(i, 0), "IMI") > 0 Then
        Param_List(i - 1, 1) = Matriz_PARAM(i, 0) & REV
    ElseIf InStr(1, Matriz_PARAM(i, 0), "FECHA") > 0 Then
        Param_List(i - 1, 1) = Matriz_PARAM(i, 0) & REV
    ElseIf InStr(1, Matriz_PARAM(i, 0), "REV_") > 0 Then
        Param_List(i - 1, 1) = Matriz_PARAM(i, 0) & REV
    Else
        Param_List(i - 1, 1) = Matriz_PARAM(i, 0)
    End If
    
    Param_List(i - 1, 2) = Matriz_PARAM(i, 1)

Next

End Sub

Attribute VB_Name = "Module3"
Sub CATMain()

End Sub

Attribute VB_Name = "Puntos_Excel"
Sub CATMain()
Set OBJXL = CreateObject("Excel.Application")
Datei = "C:\Users\assain\Desktop\RELEVAMIENTO TRAKER F50\TXT\Sesiones de palpado MEDIDO\Archivo de PUNTOS COMPLETO DATOS.xlsx"
'"C:\Users\assain\Desktop\RELEVAMIENTO TRAKER F50\TXT\BARQUILLA IZQ.xlsx"

OBJXL.Workbooks.Open FileName:=Datei, ReadOnly:=True
OBJXL.Visible = True
OBJXL.ActiveSheet.Activate

Dim partDocument1 As PartDocument
Set partDocument1 = CATIA.ActiveDocument

Dim part1 As Part
Set part1 = partDocument1.Part

Dim hybridBodies1 As HybridBodies
Set hybridBodies1 = part1.HybridBodies

Dim hybridBody1 As HybridBody

part1.Update

'For i = 1 To 150000
'
'
'
'        XP = OBJXL.Worksheets(1).Cells(i, 1)
'        YP = OBJXL.Worksheets(1).Cells(i, 2)
'        ZP = OBJXL.Worksheets(1).Cells(i, 3)
'
'do while
'
'        If XP <> "#" Then
'            Dim hybridShapeFactory1 As HybridShapeFactory
'            Set hybridShapeFactory1 = part1.HybridShapeFactory
'
'            Dim hybridShapePointCoord1 As HybridShapePointCoord
'
'            Set hybridShapePointCoord1 = hybridShapeFactory1.AddNewPointCoord(XP, YP, ZP)
'
'            hybridBody1.AppendHybridShape hybridShapePointCoord1
'
'            part1.InWorkObject = hybridShapePointCoord1
'
'        ElseIf XP = "" Then
'
'
'
'        Else
'
'        Set hybridBody1 = hybridBodies1.Add()
'        part1.Update
'
'        End If
'
'
'Next
'
'part1.Update


For i = 1 To 8000



        XP = OBJXL.Worksheets(1).Cells(i, 1)
        YP = OBJXL.Worksheets(1).Cells(i, 2)
        ZP = OBJXL.Worksheets(1).Cells(i, 3)

        If XP <> "#" Then
            Dim hybridShapeFactory1 As HybridShapeFactory
            Set hybridShapeFactory1 = part1.HybridShapeFactory

            Dim hybridShapePointCoord1 As HybridShapePointCoord

            Set hybridShapePointCoord1 = hybridShapeFactory1.AddNewPointCoord(XP, YP, ZP)

            hybridBody1.AppendHybridShape hybridShapePointCoord1

            part1.InWorkObject = hybridShapePointCoord1

        ElseIf XP = "" Then



        Else

        Set hybridBody1 = hybridBodies1.Add()
        part1.Update

        End If


Next

part1.Update


End Sub

Attribute VB_Name = "Seleccionar_Carpera_PDMFIG"
Sub SeleccionRutaPDMFig(RUTA_ENTRADA, RUTA_SALIDA, NO_ELIGE)
        
'=================================================================================================
' TITLE: BrowseForFolderDialogBox
'
' PURPOSE: Open Window dialog box to choose directory to process.
' Return the choosen path to a variable.
'
' HOW TO USE: strResult = BrowseForFolderDialogBox()
' ==================================================

Const WINDOW_HANDLE = 0
Const NO_OPTIONS = &H1
Dim objShellApp
Dim objFolder
Dim objFldrItem
Dim objPath

Set objShellApp = CreateObject("Shell.Application")
Set objFolder = objShellApp.BrowseFor * Folder(WINDOW_HANDLE, "Seleccione la carpeta donde desea liberar el archivo DD3.", 0, RUTA_ENTRADA)

'~ If IsNoData(objFolder) Then
'~ WScript.Echo "You choose to cancel. This will stop this script."
'~ Wscript.Quit
'~ Else
'~ Set objFldrItem = objFolder.Self
'~ objPath = objFldrItem.Path

BrowseForFolderDialogBox = objPath

On Error Resume Next
NO_ELIGE = False
If objFolder = "" Then
    NO_ELIGE = True
End If
If Err.Number <> 0 Then
    NO_ELIGE = True
End If

RUTA_SALIDA = RUTA_ENTRADA & objFolder & "\"

Set objShellApp = Nothing
Set objFolder = Nothing
Set objFldrItem = Nothing

ERROR_SALE:

End Sub

Attribute VB_Name = "UserForm1"
Attribute VB_Base = "0{A679004D-4B7B-4ABB-8D96-6BC9D24A0910}{FDABE3E1-012A-4A5F-B8F0-9A1CB6688F54}"
Attribute VB_GlobalNameSpace = False
Attribute VB_Creatable = False
Attribute VB_PredeclaredId = True
Attribute VB_Exposed = False
Attribute VB_TemplateDerived = False
Attribute VB_Customizable = False


Private Sub CommandButton1_Click()

Dim Ruta_Plantilla As String

Dim documents1 As Documents
Set documents1 = CATIA.Documents

Call PROYECTO(PROY_CODE, PROYS, ARM_SYS)

Call Rutas("PLANTILLAS_2D", RUTA_SALIDA, PROY_CODE)

opc = ComboBox1.Value
    
    If opc <> "" Then
    
        Hide
        
        Ruta_Plantilla = RUTA_SALIDA & opc & ".CATDrawing"
        
        Dim drawingDocument1 As DrawingDocument
        Set drawingDocument1 = documents1.NewFrom(Ruta_Plantilla)
        
        Dim drawingSheets1 As DrawingSheets
        Set drawingSheets1 = drawingDocument1.Sheets
        
        Dim drawingSheet1 As DrawingSheet
        Set drawingSheet1 = drawingSheets1.ITEM(1)
        
        drawingSheet1.Activate
        
        Set parameters1 = drawingDocument1.Parameters
        
        Set strParam1 = parameters1.ITEM("Drawing\DISEŃO")
        
        strParam1.Value = UCase(Environ$("username"))
        
        Dim parameters2 As Parameters
        Set parameters2 = drawingDocument1.Parameters
        
        Dim strParam2 As StrParam
        Set strParam2 = parameters2.ITEM("Drawing\NUMERO DE PLANO")
    
        strParam2.Value = UCase(PN)
        
        Dim parameters3 As Parameters
        Set parameters3 = drawingDocument1.Parameters
        
        Dim strParam3 As StrParam
        Set strParam3 = parameters3.ITEM("Drawing\DESIGNACION PRINCIPAL")
    
        strParam3.Value = UCase(DESC)
        
        Dim parameters4 As Parameters
        Set parameters4 = drawingDocument1.Parameters
        
        Dim strParam4 As StrParam
        Set strParam4 = parameters4.ITEM("Drawing\CODIGO DE UTILIZACION")
    
        strParam4.Value = PROY_CODE
        
        Dim parameters6 As Parameters
        Set parameters6 = drawingDocument1.Parameters

        Dim strParam6 As StrParam
        Set strParam6 = parameters6.ITEM("Drawing\PROXIMO CONJUNTO")

        strParam6.Value = CSI
    
    Else
        MsgBox "Seleccione un formato de hoja o retírese.", vbCritical
    End If
    
End Sub

Private Sub UserForm_Initialize()

With ComboBox1
        .AddItem "A0"
        .AddItem "A1"
        .AddItem "A2"
        .AddItem "A3"
        .AddItem "A4"
End With

opc = ComboBox1.Value

End Sub

Public Property Get coso() As String
    coso = ComboBox1.Value
End Property

Attribute VB_Name = "UserForm2"
Attribute VB_Base = "0{1D7ADE05-6C83-45B8-A0A1-0ED8FB7C1445}{158EDD2A-CC44-492B-9BFA-2F19CFD03FD3}"
Attribute VB_GlobalNameSpace = False
Attribute VB_Creatable = False
Attribute VB_PredeclaredId = True
Attribute VB_Exposed = False
Attribute VB_TemplateDerived = False
Attribute VB_Customizable = False


Private Sub CommandButton1_Click()

If OptionButton1.Value = True Then
    DF = 0
ElseIf OptionButton2 = True Then
    DF = 1
End If

Unload UserForm2

End Sub

Private Sub CommandButton2_Click()

DF = -1
Unload UserForm2

End Sub

Private Sub Frame1_Click()

End Sub

Private Sub OptionButton1_Click()

End Sub

Private Sub OptionButton2_Click()

End Sub

Attribute VB_Name = "UserForm3"
Attribute VB_Base = "0{A868CC2F-E9DE-4DC1-B0BF-E26D6D383CF0}{40627A5B-7F34-4DA2-98F2-33E3A19A2AAB}"
Attribute VB_GlobalNameSpace = False
Attribute VB_Creatable = False
Attribute VB_PredeclaredId = True
Attribute VB_Exposed = False
Attribute VB_TemplateDerived = False
Attribute VB_Customizable = False




Private Sub CommandButton1_Click()
Dim N_CAP_TOT As Integer
Dim VISTAS() As Variant

Dim p As Parameter
Dim tecno As String

If TypeName(CATIA.ActiveDocument) = "ProductDocument" Then
    'Dim PARTE As Product
    Set PARTE = CATIA.ActiveDocument.Product
ElseIf TypeName(CATIA.ActiveDocument) = "PartDocument" Then
    'Dim PARTE As Part
    Set PARTE = CATIA.ActiveDocument.Part
End If
    'Set p = parte.Parameters.ITEM("Tipo")
    'tecno = p.ValueAsString


N_CAP_TOT = Int(ComboBox1.Value) + Int(ComboBox2.Value) + Int(ComboBox3.Value) + Int(ComboBox4.Value) _
+ Int(ComboBox5.Value) + Int(ComboBox6.Value) + Int(ComboBox7.Value) + Int(ComboBox8.Value)

ReDim VISTAS(1 To N_CAP_TOT)

N_CAP_NONE = Int(ComboBox1.Value)
N_CAP_HOLE = Int(ComboBox2.Value)
N_CAP_ORD = Int(ComboBox8.Value)
N_CAP_BOND = Int(ComboBox3.Value)
N_CAP_VIEW = Int(ComboBox4.Value)
N_CAP_ID = Int(ComboBox5.Value)
N_CAP_ALL = Int(ComboBox6.Value)
N_CAP_NOTES = Int(ComboBox7.Value)

N_AUX = 0
For i = 1 To N_CAP_NONE
    N_TOT = N_TOT + 1
    If N_CAP_NONE = 1 Then
        VISTAS(i) = Format(N_TOT, "00") & "_NONE" & " "
    Else
        N_AUX = N_AUX + 1
        VISTAS(i) = Format(N_TOT, "00") & "_NONE" & " " & N_AUX
    End If
Next

N_AUX = 0
For i = N_TOT + 1 To N_TOT + N_CAP_HOLE
    N_TOT = N_TOT + 1
    If N_CAP_HOLE = 1 Then
        VISTAS(i) = Format(N_TOT, "00") & "_HOLES" & " "
    Else
        N_AUX = N_AUX + 1
        VISTAS(i) = Format(N_TOT, "00") & "_HOLES" & " " & N_AUX
    End If
Next

N_AUX = 0
For i = N_TOT + 1 To N_TOT + N_CAP_ORD
    N_TOT = N_TOT + 1
    If N_CAP_ORD = 1 Then
        VISTAS(i) = Format(N_TOT, "00") & "_ORDER" & " "
    Else
        N_AUX = N_AUX + 1
        VISTAS(i) = Format(N_TOT, "00") & "_ORDER" & " " & N_AUX
    End If
Next

N_AUX = 0
For i = N_TOT + 1 To N_TOT + N_CAP_BOND
    N_TOT = N_TOT + 1
    If N_CAP_BOND = 1 Then
        VISTAS(i) = Format(N_TOT, "00") & "_BONDING" & " "
    Else
        N_AUX = N_AUX + 1
        VISTAS(i) = Format(N_TOT, "00") & "_BONDING" & " " & N_AUX
    End If
Next

N_AUX = 0
For i = N_TOT + 1 To N_TOT + N_CAP_VIEW
    N_TOT = N_TOT + 1
    If N_CAP_VIEW = 1 Then
        VISTAS(i) = Format(N_TOT, "00") & "_VIEW" & " "
    Else
        N_AUX = N_AUX + 1
        VISTAS(i) = Format(N_TOT, "00") & "_VIEW" & " " & N_AUX
    End If
Next

N_AUX = 0
For i = N_TOT + 1 To N_TOT + N_CAP_ID
    N_TOT = N_TOT + 1
    If N_CAP_ID = 1 Then
        VISTAS(i) = Format(N_TOT, "00") & "_ID" & " "
    Else
        N_AUX = N_AUX + 1
        VISTAS(i) = Format(N_TOT, "00") & "_ID" & " " & N_AUX
    End If
Next

N_AUX = 0
For i = N_TOT + 1 To N_TOT + N_CAP_ALL
    N_TOT = N_TOT + 1
    If N_CAP_ALL = 1 Then
        VISTAS(i) = Format(N_TOT, "00") & "_ALL" & " "
    Else
        N_AUX = N_AUX + 1
        VISTAS(i) = Format(N_TOT, "00") & "_ALL" & " " & N_AUX
    End If
Next

N_AUX = 0
For i = N_TOT + 1 To N_TOT + N_CAP_NOTES
    N_TOT = N_TOT + 1
    If N_CAP_NOTES = 1 Then
        VISTAS(i) = Format(N_TOT, "00") & "_NOTES" & " "
    Else
        N_AUX = N_AUX + 1
        VISTAS(i) = Format(N_TOT, "00") & "_NOTES" & " " & N_AUX
    End If
Next

Call FTA_generator(PARTE, VISTAS)

Unload UserForm3
'For i = 1 To N_TOT
'MsgBox VISTAS(i)
'Next

End Sub
Private Sub CheckBox2_Click()

If CheckBox2.Value = False Then
    ComboBox2.BorderColor = &H80000006
    ComboBox2.Enabled = False
    ComboBox2.Value = 0
ElseIf CheckBox2.Value = True Then
    ComboBox2.BorderColor = &H8000000D
    ComboBox2.Enabled = True
    ComboBox2.Value = 1
End If

End Sub

Private Sub CheckBox3_Click()

If CheckBox3.Value = False Then
    ComboBox3.BorderColor = &H80000006
    ComboBox3.Enabled = False
    ComboBox3.Value = 0
ElseIf CheckBox3.Value = True Then
    ComboBox3.BorderColor = &H8000000D
    ComboBox3.Enabled = True
    ComboBox3.Value = 1
End If

End Sub

Private Sub CheckBox4_Click()

If CheckBox4.Value = False Then
    ComboBox4.BorderColor = &H80000006
    ComboBox4.Enabled = False
    ComboBox4.Value = 0
ElseIf CheckBox4.Value = True Then
    ComboBox4.BorderColor = &H8000000D
    ComboBox4.Enabled = True
    ComboBox4.Value = 1
End If

End Sub

Private Sub CheckBox5_Click()

If CheckBox5.Value = False Then
    ComboBox5.BorderColor = &H80000006
    ComboBox5.Enabled = False
    ComboBox5.Value = 0
ElseIf CheckBox5.Value = True Then
    ComboBox5.BorderColor = &H8000000D
    ComboBox5.Enabled = True
    ComboBox5.Value = 1
End If

End Sub
Private Sub CheckBox8_Click()

If CheckBox8.Value = False Then
    ComboBox8.BorderColor = &H80000006
    ComboBox8.Enabled = False
    ComboBox8.Value = 0
ElseIf CheckBox8.Value = True Then
    ComboBox8.BorderColor = &H8000000D
    ComboBox8.Enabled = True
    ComboBox8.Value = 1
End If

End Sub

Private Sub ComboBox2_Change()

If ComboBox2.Value > 5 Then
    ComboBox2.Value = 5
End If

End Sub

Private Sub ComboBox3_Change()

If ComboBox3.Value > 5 Then
    ComboBox3.Value = 5
End If

End Sub

Private Sub ComboBox4_Change()

If ComboBox4.Value > 5 Then
    ComboBox4.Value = 5
End If

End Sub

Private Sub ComboBox5_Change()

If ComboBox5.Value > 5 Then
    ComboBox5.Value = 5
End If

End Sub

Private Sub ComboBox7_Change()

If ComboBox7.Value > 5 Then
    ComboBox7.Value = 5
End If

End Sub
Private Sub ComboBox8_Change()

If ComboBox8.Value > 5 Then
    ComboBox8.Value = 5
End If

End Sub

Private Sub Frame1_Click()

End Sub

Private Sub UserForm_Click()

End Sub

Private Sub UserForm_Initialize()

With ComboBox2
        .AddItem 1
        .AddItem 2
        .AddItem 3
        .AddItem 4
        .AddItem 5
End With
With ComboBox3
        .AddItem 1
        .AddItem 2
        .AddItem 3
        .AddItem 4
        .AddItem 5
End With
With ComboBox8
        .AddItem 1
        .AddItem 2
        .AddItem 3
        .AddItem 4
        .AddItem 5
End With
With ComboBox4
        .AddItem 1
        .AddItem 2
        .AddItem 3
        .AddItem 4
        .AddItem 5
End With
With ComboBox5
        .AddItem 1
        .AddItem 2
        .AddItem 3
        .AddItem 4
        .AddItem 5
End With
With ComboBox7
        .AddItem 1
        .AddItem 2
        .AddItem 3
        .AddItem 4
        .AddItem 5
End With


End Sub

Attribute VB_Name = "UserForm4"
Attribute VB_Base = "0{CAF2B0C5-A260-4D2B-B47F-B6082B9DF711}{81FAAE29-FEFD-4496-88DC-40952EA9D8A0}"
Attribute VB_GlobalNameSpace = False
Attribute VB_Creatable = False
Attribute VB_PredeclaredId = True
Attribute VB_Exposed = False
Attribute VB_TemplateDerived = False
Attribute VB_Customizable = False



Private Sub CommandButton1_Click()

If OptionButton1.Value = True Then
    opc = 0
ElseIf OptionButton2 = True Then
    opc = 1
ElseIf OptionButton3 = True Then
    opc = 2
End If
Unload UserForm4

End Sub

Private Sub CommandButton2_Click()

opc = -1
Unload UserForm4

End Sub




Private Sub Frame1_Click()

End Sub

Private Sub OptionButton1_Click()

End Sub

Private Sub OptionButton2_Click()

End Sub

Attribute VB_Name = "UserForm5"
Attribute VB_Base = "0{29015401-6870-4F54-9805-8851E8C707B5}{C8E934ED-8E30-43A6-97D9-89F1A73B6CF0}"
Attribute VB_GlobalNameSpace = False
Attribute VB_Creatable = False
Attribute VB_PredeclaredId = True
Attribute VB_Exposed = False
Attribute VB_TemplateDerived = False
Attribute VB_Customizable = False




Private Sub CheckBox1_Click()

If CheckBox1.Value = False Then
    TextBox3.Value = ""
    ComboBox1.Clear
    ComboBox4.Clear
    Call Carga_Codigo
    UserForm5.Width = 321
Else
    UserForm5.Width = 430
End If

End Sub

Private Sub ComboBox1_Change()
Dim ATA_TEXT(1 To 1600, 1 To 110) As Variant

ComboBox4.ListIndex = ComboBox1.ListIndex

If ComboBox1.Value <> "" Then

    Entrada = ComboBox1.Value
    
    B_Entrada = False
    For i = 0 To ComboBox1.ListCount
        If i = ComboBox1.ListCount Then
            Exit For
        End If
        If Entrada = ComboBox1.List(i) Then
            B_Entrada = True
            Exit For
        End If
    Next

    If B_Entrada = True Then
        Call Carga_Texto(ATA_TEXT())
        
        Combo = Split(ComboBox1.Value, "-")
        Valor = Combo(0) & Combo(1)
        Encontro = False
        
        For i = 1 To 1600
            If Valor = Left(ATA_TEXT(i, 1), 4) Then
                TextBox2.Value = ATA_TEXT(i + 1, 1)
                'MsgBox Valor & "-" & Left(ATA_TEXT(i, 1), 4)
                Encontro = True
                Exit For
            End If
        Next
        
        If Encontro = False Then
            For i = 1 To 1600
                If Left(Valor, 2) = Left(ATA_TEXT(i, 1), 2) And Mid(ATA_TEXT(i, 1), 3, 1) = " " Then
                    'MsgBox Left(Valor, 2) & "|-|" & Left(ATA_TEXT(i, 1), 2) & "|---|" & Mid(ATA_TEXT(i, 1), 3, 1) & "|-|" & ATA_TEXT(i, 1)
                    TextBox2.Value = "Título."
                    Exit For
                End If
            Next
        End If
    End If
End If

End Sub


Private Sub ComboBox4_Change()

ComboBox1.ListIndex = ComboBox4.ListIndex

End Sub


Private Sub CommandButton1_Click()

If Len(TextBox1.Value) < 2 Then
    MsgBox "El formato de codigo (XX-XX-XX) no es válido.", vbCritical, "Error formato.."
ElseIf IsNumeric(TextBox1.Value) = False Then
    MsgBox "El formato de codigo (XX-XX-XX) no es válido. Debe ser numérico.", vbCritical, "Introduzca números.."
Else
    If Len(ComboBox1.Value) = 6 Then
        ATA_CODE = ComboBox1.Value & TextBox1.Value
    ElseIf Len(ComboBox1.Value) = 3 Then
        ATA_CODE = ComboBox1.Value & "00-00"
    End If
    'MsgBox ATA_CODE
    Unload UserForm5
End If

opc = 0

End Sub

Private Sub CommandButton2_Click()

opc = -1
Unload UserForm5

End Sub


Private Sub TextBox3_Change()

Dim ATA_TEXT(1 To 1600, 1 To 110) As Variant

If Len(TextBox3.Value) < 3 Then
    ComboBox1.Clear
    ComboBox4.Clear
    Call Carga_Codigo
Else
    Call Carga_Texto(ATA_TEXT())
    ComboBox1.Clear
    ComboBox4.Clear
    For i = 1 To 1600
        Encontro = False
        For j = 2 To 110
            If UCase(ATA_TEXT(i, j)) = UCase(TextBox3.Value) And Encontro = False Then
                Encontro = True
                If IsNumeric(ATA_TEXT(i, 2)) = True Then
                    If Len(ATA_TEXT(i, 2)) = 4 And ULTIMO <> Left(ATA_TEXT(i, 2), 2) & "-" & Right(ATA_TEXT(i, 2), 2) Then
                        ComboBox1.AddItem Left(ATA_TEXT(i, 2), 2) & "-" & Right(ATA_TEXT(i, 2), 2)
                        ComboBox4.AddItem UCase(Mid(ATA_TEXT(i, 1), 6))
                        ULTIMO = Left(ATA_TEXT(i, 2), 2) & "-" & Right(ATA_TEXT(i, 2), 2)
                    ElseIf Len(ATA_TEXT(i, 2)) = 2 And ULTIMO <> Left(ATA_TEXT(i, 2), 2) & "-" Then
                        ComboBox1.AddItem Left(ATA_TEXT(i, 2), 2) & "-"
                        ComboBox4.AddItem UCase(Mid(ATA_TEXT(i, 1), 6))
                        ULTIMO = Left(ATA_TEXT(i, 2), 2) & "-"
                    End If
                ElseIf IsNumeric(ATA_TEXT(i, 2)) = False Then
                    If Len(ATA_TEXT(i - 1, 2)) = 4 And ULTIMO <> Left(ATA_TEXT(i - 1, 2), 2) & "-" & Right(ATA_TEXT(i - 1, 2), 2) Then
                        ComboBox1.AddItem Left(ATA_TEXT(i - 1, 2), 2) & "-" & Right(ATA_TEXT(i - 1, 2), 2)
                        ComboBox4.AddItem UCase(Mid(ATA_TEXT(i - 1, 1), 6))
                        ULTIMO = Left(ATA_TEXT(i - 1, 2), 2) & "-" & Right(ATA_TEXT(i - 1, 2), 2)
                    ElseIf Len(ATA_TEXT(i - 1, 2)) = 2 And ULTIMO <> Left(ATA_TEXT(i - 1, 2), 2) & "-" Then
                        ComboBox1.AddItem Left(ATA_TEXT(i - 1, 2), 2) & "-"
                        ComboBox4.AddItem UCase(Mid(ATA_TEXT(i - 1, 1), 6))
                        ULTIMO = Left(ATA_TEXT(i - 1, 2), 2) & "-"
                    End If
                End If
            End If
            
            If Encontro = True Then
            Exit For
            End If
            
        Next
    Next


End If
End Sub


Private Sub UserForm_Initialize()

UserForm5.Width = 321
Call Carga_Codigo

ComboBox1.Value = ComboBox1.List(329)

End Sub

Sub Carga_Codigo()

Dim fsDataFile As Object
Dim sText As Object
Dim sPath As String
Dim sFullLine As String
Dim ATA(1000, 10) As Variant

'LECTURA DE LOS CÓDIGOS
Call PROYECTO(PROY_CODE, PROYS, ARM_SYS)

'Dim MAT_CODE(1000, 44) As Variant
Call Rutas("ATA", RUTA_SALIDA, PROY_CODE)

Set fsDataFile = CreateObject("Scripting.FileSystemObject")
'The fully qualified path to your lookup file
sPath = RUTA_SALIDA

'Create a text stream from your FileSystemObject
Set sText = fsDataFile.OpenTextFile(sPath, 1, False)

'Loop through each line in the text stream
Do While sText.AtEndOfStream <> True
    linea = linea + 1
    sFullLine = sText.ReadLine
    saCsvData = Split(sFullLine, ";")
    If saCsvData(1) = "" Then
        ComboBox1.AddItem saCsvData(0) & "-"
    Else
        ComboBox1.AddItem saCsvData(0) & "-" & saCsvData(1) & "-"
    End If
    
    ComboBox4.AddItem saCsvData(3)
Loop

sText.Close

End Sub

Sub Carga_Texto(ByRef ATA_TEXT As Variant)

Dim fsDataFile As Object
Dim sText As Object
Dim sPath As String
Dim sFullLine As String

Call PROYECTO(PROY_CODE, PROYS, ARM_SYS)

Call Rutas("ATA_TEXTO", RUTA_SALIDA, PROY_CODE)

Set fsDataFile = CreateObject("Scripting.FileSystemObject")

'LECTURA DE LOS TEXTOS DEL JASC
linea = 0
'The fully qualified path to your lookup file
sPath = RUTA_SALIDA
    
'Create a text stream from your FileSystemObject
Set sText = fsDataFile.OpenTextFile(sPath, 1, False)
    
'Loop through each line in the text stream
Do While sText.AtEndOfStream <> True
    linea = linea + 1
    sFullLine = sText.ReadLine
    Count = Len(sFullLine) - Len(Replace(sFullLine, ";", ""))
    saCsvData = Split(sFullLine, ";")
    For i = 1 To Count + 1
        ATA_TEXT(linea, i) = saCsvData(i - 1)
    Next
Loop

sText.Close

End Sub

Attribute VB_Name = "UserForm6"
Attribute VB_Base = "0{0E721290-2DC2-45E7-A68A-4B0948C07805}{FF3B2FF0-900F-4B4C-8669-27CE4AED0290}"
Attribute VB_GlobalNameSpace = False
Attribute VB_Creatable = False
Attribute VB_PredeclaredId = True
Attribute VB_Exposed = False
Attribute VB_TemplateDerived = False
Attribute VB_Customizable = False

Dim MAT_CODE(200, 40) As Variant
Dim N_MATERIAL As Integer
Dim MATERIAL_CODE As String
Dim ZONA_CODE As String
Dim APP_CODE As String

Private Sub CheckBox1_Click()

If CheckBox1.Value = True Then
    Frame2.ForeColor = &H8000000C
    Frame3.ForeColor = &H8000000C
    Frame4.ForeColor = &H8000000C
    Frame5.ForeColor = &H8000000C
    CheckBox1.ForeColor = &HFF&
    TextBox1.Enabled = False
    TextBox1.Value = ""
    TextBox2.Enabled = False
    TextBox2.Value = ""
    TextBox3.Enabled = False
    TextBox3.Value = ""
    ComboBox1.Enabled = False
    ComboBox2.Enabled = False
    ComboBox1.BorderColor = &H8000000C
    ComboBox2.BorderColor = &H8000000C
    ComboBox1.Value = ""
    ComboBox2.Value = ""
    OptionButton1.Value = False
    OptionButton2.Value = False
    OptionButton3.Value = False
    OptionButton4.Value = False
    OptionButton1.Enabled = False
    OptionButton2.Enabled = False
    OptionButton3.Enabled = False
    OptionButton4.Enabled = False
    Label2.Caption = ""
    Label2.Enabled = False
    MsgBox "Atención! Utilice esta opción sólo cuando la parte no tenga protección superficial alguna o la misma ya venga aplicada por el proveedor.", vbCritical, "Advertencia.."
Else
    Frame2.ForeColor = &H0&
    Frame3.ForeColor = &H0&
    Frame4.ForeColor = &H0&
    Frame5.ForeColor = &H0&
    CheckBox1.ForeColor = &H0&
    TextBox1.Enabled = True
    TextBox2.Enabled = True
    TextBox3.Enabled = True
    ComboBox1.Enabled = True
    ComboBox2.Enabled = True
    ComboBox1.BorderColor = &H8000000D
    ComboBox2.BorderColor = &H8000000D
    OptionButton1.Enabled = True
    OptionButton2.Enabled = True
    OptionButton3.Enabled = True
    OptionButton4.Enabled = True
    Label2.Enabled = True
End If

End Sub

Private Sub ComboBox1_Change()

ComboBox2.Clear
For i = 0 To 78
    If MAT_CODE(i + 8, ComboBox1.ListIndex + 3) <> "" Then
        ComboBox2.AddItem MAT_CODE(i + 8, 1)
    End If
Next

MAT_LISTO = False
For i = 0 To 40
    If MAT_CODE(6, i) = ComboBox1.Value And MAT_LISTO = False Then
        MATERIAL_CODE = Format(MAT_CODE(7, i), "00")
        MAT_LIST = True
        If APP_CODE <> "" And ZONA_CODE <> "" And MATERIAL_CODE <> "" Then
            Label2.Caption = APP_CODE & ZONA_CODE & MATERIAL_CODE
        End If
    End If
Next

ComboBox2.ListIndex = 0
TextBox2.Text = ComboBox2.Value

End Sub

Private Sub ComboBox2_Change()

ENCONTRO_APP = False
For i = 0 To 78
    If MAT_CODE(i + 8, 1) = ComboBox2.Value And ENCONTRO_APP = False Then
        TextBox3.Text = MAT_CODE(i + 8, 0)
        APP_CODE = Format(MAT_CODE(i + 8, 2), "000")
        If APP_CODE <> "" And ZONA_CODE <> "" And MATERIAL_CODE <> "" Then
            Label2.Caption = APP_CODE & ZONA_CODE & MATERIAL_CODE
        End If
        ENCONTRO_APP = True
    End If
Next

TextBox2.Text = ComboBox2.Value

End Sub

Private Sub CommandButton1_Click()

If CheckBox1.Value = False Then

    If Len(Label2.Caption) < 6 Then
        MsgBox "El formato de codigo no es válido.", vbCritical, "Error de formato.."
    Else
        PROT_SUP = Label2.Caption
        Unload UserForm6
    End If

ElseIf CheckBox1.Value = True Then
    
    PROT_SUP = "SIN PROT. SUPERFICIAL"
    Unload UserForm6

End If

opc = 0

End Sub

Private Sub CommandButton2_Click()
opc = -1
Unload UserForm6
End Sub


Private Sub OptionButton1_Click()

TextBox1.Text = MAT_CODE(1, 3)
ZONA_CODE = "A"
        If APP_CODE <> "" And ZONA_CODE <> "" And MATERIAL_CODE <> "" Then
            Label2.Caption = APP_CODE & ZONA_CODE & MATERIAL_CODE
        End If

End Sub

Private Sub OptionButton2_Click()

TextBox1.Text = MAT_CODE(2, 3)
ZONA_CODE = "B"
        If APP_CODE <> "" And ZONA_CODE <> "" And MATERIAL_CODE <> "" Then
            Label2.Caption = APP_CODE & ZONA_CODE & MATERIAL_CODE
        End If

End Sub

Private Sub OptionButton3_Click()
TextBox1.Text = MAT_CODE(3, 3)
ZONA_CODE = "C"
        If APP_CODE <> "" And ZONA_CODE <> "" And MATERIAL_CODE <> "" Then
            Label2.Caption = APP_CODE & ZONA_CODE & MATERIAL_CODE
        End If
End Sub

Private Sub OptionButton4_Click()
TextBox1.Text = MAT_CODE(4, 3)
ZONA_CODE = "D"
        If APP_CODE <> "" And ZONA_CODE <> "" And MATERIAL_CODE <> "" Then
            Label2.Caption = APP_CODE & ZONA_CODE & MATERIAL_CODE
        End If
End Sub

Private Sub OptionButton5_Click()

MsgBox "Atención! Sólo tildar esta opción si se trata efectivamente de una parte a la que no aplica proteccón superficial alguna.", vbCritical

End Sub

Private Sub UserForm_Initialize()

Call PROYECTO(PROY_CODE, PROYS, ARM_SYS)

'Dim MAT_CODE(1000, 44) As Variant
Call Rutas("PROT", RUTA_SALIDA, PROY_CODE)


Set fsDataFile = CreateObject("Scripting.FileSystemObject")
'The fully qualified path to your lookup file
sPath = RUTA_SALIDA

'Create a text stream from your FileSystemObject
Set sText = fsDataFile.OpenTextFile(sPath, 1, False)

'Loop through each line in the text stream
Do While sText.AtEndOfStream <> True
    linea = linea + 1
    sFullLine = sText.ReadLine
    saCsvData = Split(sFullLine, ";")
    For i = 0 To 40
        MAT_CODE(linea, i) = saCsvData(i)
    Next
Loop

For i = 3 To 40
    ComboBox1.AddItem MAT_CODE(6, i)
Next

For i = 8 To 83
    ComboBox2.AddItem MAT_CODE(i, 1)
Next

sText.Close
End Sub

Attribute VB_Name = "UserForm7"
Attribute VB_Base = "0{DFE73DF6-ABA3-459B-866B-F4CCEB5E735C}{5E62DF5E-E779-42B5-A564-42E6C679E83E}"
Attribute VB_GlobalNameSpace = False
Attribute VB_Creatable = False
Attribute VB_PredeclaredId = True
Attribute VB_Exposed = False
Attribute VB_TemplateDerived = False
Attribute VB_Customizable = False


Private Sub CommandButton1_Click()

If Len(ComboBox1.Value) < 15 Then
    MsgBox "El P/N seleccionado no es válido.", vbCritical
Else
    N_CSI = ComboBox1.Value
    Unload UserForm7
End If

End Sub

Private Sub CommandButton2_Click()
Unload UserForm7
End Sub

Private Sub UserForm_Initialize()

'Genera un array de CSIs
Call PROYECTO(PROY_CODE, PROYS, ARM_SYS)

Call Columnas_EP(ARR_COLUMNAS, COL_LIMITE, PROY_CODE)

Set OBJXL = CreateObject("Excel.Application")
Call Rutas("ESTRUCTURA", RUTA_SALIDA, PROY_CODE)
Datei = RUTA_SALIDA
OBJXL.Workbooks.Open FileName:=Datei, ReadOnly:=True
OBJXL.Visible = False
OBJXL.ActiveSheet.Activate

no_pn = False

'ARR_COLUMNAS (1) 'NIVEL
'ARR_COLUMNAS (3) 'CSI
'ARR_COLUMNAS (4) 'NRO_ORD
'ARR_COLUMNAS (2) 'NRO_PARTE
'ARR_COLUMNAS (5) 'DES
'ARR_COLUMNAS (6) 'TEC
'ARR_COLUMNAS (9) 'CANT
'ARR_COLUMNAS (10) 'AUTOR
'ARR_COLUMNAS (8) 'MAT
'ARR_COLUMNAS (12) 'REVISOR POR FABRICACIÓN
'ARR_COLUMNAS (13) 'ESTADO POR FABRICACIÓN
'ARR_COLUMNAS (14) 'REVISOR PLANOS O TECNICO
'ARR_COLUMNAS (15) 'ESTADO PLANOS O TECNICO
'ARR_COLUMNAS (16) 'REVISOR POR INGENIERO SISTEMAS
'ARR_COLUMNAS (17) 'ESTADO POR INGENIERO SISTEMAS
'ARR_COLUMNAS (18) 'REVISOR POR CALCULO ESTRUCTURAL
'ARR_COLUMNAS (19) 'ESTADO POR CALCULO ESTRUCTURAL
'ARR_COLUMNAS (20) 'REVISOR APROBADOR
'ARR_COLUMNAS (21) 'ESTADO APROBADOR
'ARR_COLUMNAS (22) 'DISTANCIA ENTRE BLOQUES DE APROBADORES

For i = 1 To 3000
    If UCase(PN) = UCase(OBJXL.Worksheets(1).Cells(i, CInt(ARR_COLUMNAS(2)))) Then
        'SE DECLARA QUE ENTRÓ (HUBO COINCIDENCIA)
        ComboBox1.AddItem UCase(OBJXL.Worksheets(1).Cells(i, CInt(ARR_COLUMNAS(3))))
        no_pn = True
    End If
Next

AUX_EXCEL = Split(RUTA_SALIDA, "\")

OBJXL.Workbooks(AUX_EXCEL(UBound(AUX_EXCEL))).Close SaveChanges:=False

If ComboBox1.ListCount = 1 Then
    ComboBox1.ListIndex = 0
    ComboBox1.Locked = True
End If


End Sub

Attribute VB_Name = "UserForm8"
Attribute VB_Base = "0{716D7AC0-2FA8-46C2-AE62-EBC2F6B1007A}{61A9E520-1E7A-4436-B8F8-01DD15630A3F}"
Attribute VB_GlobalNameSpace = False
Attribute VB_Creatable = False
Attribute VB_PredeclaredId = True
Attribute VB_Exposed = False
Attribute VB_TemplateDerived = False
Attribute VB_Customizable = False



Private Sub Image1_Click()

i = 1
nimages = 60

Do While i < nimages

    Fname = "C:\Users\assain\Desktop\ASSAIN\Frames\" & i & ".gif"
    Image1.Picture = LoadPicture("C:\Users\assain\Desktop\ASSAIN\Frames\" & i & ".gif")

    j = 2
    Call L_Pause(j)

    i = i + 1
Loop

Image1.Picture = LoadPicture(Fname)
Debug.Print Fname

End Sub

Private Sub UserForm_Click()

End Sub

Sub test_LoopTime()


End Sub


Sub L_Pause(k)

For i = 1 To 2 ^ k

Next i
End Sub





Private Sub UserForm_Initialize()


End Sub

Attribute VB_Name = "UserForm9"
Attribute VB_Base = "0{217D24A8-A02A-44F9-9BA5-955483AB201E}{CAE48086-8845-4DE0-9EBC-F8C5BCB4F2B5}"
Attribute VB_GlobalNameSpace = False
Attribute VB_Creatable = False
Attribute VB_PredeclaredId = True
Attribute VB_Exposed = False
Attribute VB_TemplateDerived = False
Attribute VB_Customizable = False

Dim PN_COSO As Variant
Dim FILTRADO As Boolean
Dim PN_COSO_AUX As Variant
Dim PN_COSO_AUX_2(1 To 300, 1 To 20) As Variant
Dim bMakeItHappen As Boolean
Dim Matriz_MATERIAL As Variant

Private Sub CheckBox1_Click()

UserForm9.Width = 1046
ListBox1.Width = UserForm9.Width - 26

If CheckBox1.Value = True Then

    MsgBox "Esta opción está pensada para incluir resinas, acelerantes y fibras en una pieza de material compuesto.", vbInformation
    ComboBox1.Enabled = False
    Frame12.Visible = False
    Frame6.Visible = False
    Frame7.Visible = False
    Frame14.Visible = False

    BOOL_MAT_PRIM = True
    Call Lectura_Mat(PN_COSO_AUX_2, ComboBox1.Value)
    Call Fill(PN_COSO_AUX_2, BOOL_MAT_PRIM)

ElseIf CheckBox1.Value = False Then

    ComboBox1.Enabled = True
    Frame12.Visible = True
    Frame6.Visible = True
    Frame7.Visible = True
    Frame14.Visible = True
    
    BOOL_MAT_PRIM = False
    Call Lectura(PN_COSO, ComboBox1.Value)
    Call Fill(PN_COSO, BOOL_MAT_PRIM)

End If

End Sub
Private Sub Lectura_Mat(Matriz_MATERIAL, PROY_CODE)

Dim fsDataFile As Object
Dim sText As Object
Dim sPath As String
Dim sFullLine As String

'LECTURA DE LOS CÓDIGOS
Call PROYECTO(PROY_CODE, PROYS, ARM_SYS)

'Dim MAT_CODE(1000, 44) As Variant
Call Rutas("MATERIAL", RUTA_SALIDA, PROY_CODE)

Set fsDataFile = CreateObject("Scripting.FileSystemObject")
'The fully qualified path to your lookup file
sPath = RUTA_SALIDA

'Create a text stream from your FileSystemObject
Set sText = fsDataFile.OpenTextFile(sPath, 1, False)

'Loop through each line in the text stream
i = 0
Do While sText.AtEndOfStream <> True
    sFullLine = sText.ReadLine
    saCsvData = Split(sFullLine, ";")
    i = i + 1
    For j = 0 To UBound(saCsvData)
        Matriz_MATERIAL(i, j + 1) = saCsvData(j)
    Next
Loop

sText.Close

End Sub
Private Sub CommandButton1_Click()

If BOOL_MAT_PRIM = False Then

    AVANZA = True
    Call PROYECTO(PROY_CODE, PROYS, ARM_SYS)

    PROY_CODE = ComboBox1.Value

    Call Columnas_EP(ARR_COLUMNAS, COL_LIMITE, PROY_CODE)
    Call Param_PN(ARR_PN, PROY_CODE)

    If FILTRADO = False Then

        'CHEQUEO DEL ARCHIVO EN LA CARPETA DE PROCESOS
        '======================================================================================================
        Call Rutas("PROCESO", RUTA_SALIDA, PROY_CODE)
        Grupo = Mid(PN_COSO(ListBox1.ListIndex + 3, ARR_COLUMNAS(2)), ARR_PN(2), 1)
        Ruta = RUTA_SALIDA & Grupo & "00\3D\"
        Nombre_Ruta = Ruta & PN_COSO(ListBox1.ListIndex + 3, ARR_COLUMNAS(2)) & "_" & PN_COSO(ListBox1.ListIndex + 3, ARR_COLUMNAS(5))
        Archivo_Existente_Part = CATIA.FileSystem.FileExists(Nombre_Ruta & ".CATPart")
        Archivo_Existente_Prod = CATIA.FileSystem.FileExists(Nombre_Ruta & ".CATProduct")

        If Archivo_Existente_Part = True Or Archivo_Existente_Prod = True Then
            MsgBox "El archivo ya existe, debe borrarlo del servidor para poder crear uno nuevo.", vbCritical
            AVANZA = False
        End If
        '=======================================================================================================

        'CHEQUEO DEL ARCHIVO EN LA CARPETA DE DOCUMENTACIÓN TÉCNICA
        '============================================================================================================================================
        Call Rutas("DD3_ACCESS", RUTA_SALIDA, PROY_CODE)

        ITERACION = 0
        For k = 1 To 8
            REV = Chr(k + 64)
            Nombre_Ruta = RUTA_SALIDA & "DD3-" & PN_COSO(ListBox1.ListIndex + 3, ARR_COLUMNAS(2)) & "-" & REV
            Archivo_Existente_Aux = CATIA.FileSystem.FileExists(Nombre_Ruta & ".CATPart")
            If Archivo_Existente_Aux = True Then
                ITERACION = ITERACION + 1
                Archivo_Existente = True
            End If
        Next

        If Archivo_Existente = True Then
            MsgBox "El archivo existe y está liberado con letra de revisión '" & Chr(ITERACION + 64) & "', considere hacer una revisión.", vbCritical
            AVANZA = False
        End If
        '============================================================================================================================================

        If AVANZA = True Then
            If ListBox1.Value <> "" Then
                STR_NIV = ListBox1.Value
            Else
                STR_NIV = 0
            End If
            On Error Resume Next
            STR_CSI = PN_COSO(ListBox1.ListIndex + 3, ARR_COLUMNAS(3))
            STR_NORD = PN_COSO(ListBox1.ListIndex + 3, ARR_COLUMNAS(4))
            STR_PN = PN_COSO(ListBox1.ListIndex + 3, ARR_COLUMNAS(2))
            STR_DES = PN_COSO(ListBox1.ListIndex + 3, ARR_COLUMNAS(5))
            STR_CANT = PN_COSO(ListBox1.ListIndex + 3, ARR_COLUMNAS(9))
            STR_AUT = PN_COSO(ListBox1.ListIndex + 3, ARR_COLUMNAS(10))
            NO_CREAR = False
            On Error GoTo 0
        End If
    Else

        'CHEQUEO DEL ARCHIVO EN LA CARPETA DE PROCESOS
        '======================================================================================================
        Call Rutas("PROCESO", RUTA_SALIDA, PROY_CODE)
        Grupo = Mid(PN_COSO_AUX(ListBox1.ListIndex + 3, ARR_COLUMNAS(2)), ARR_PN(2), 1)
        Ruta = RUTA_SALIDA & Grupo & "00\3D\"
        Nombre_Ruta = Ruta & PN_COSO_AUX(ListBox1.ListIndex + 3, ARR_COLUMNAS(2)) & "_" & PN_COSO_AUX(ListBox1.ListIndex + 3, ARR_COLUMNAS(5))
        Archivo_Existente_Part = CATIA.FileSystem.FileExists(Nombre_Ruta & ".CATPart")
        Archivo_Existente_Prod = CATIA.FileSystem.FileExists(Nombre_Ruta & ".CATProduct")

        If Archivo_Existente_Part = True Or Archivo_Existente_Prod = True Then
            MsgBox "El archivo ya existe, debe borrarlo del servidor para poder crear uno nuevo.", vbCritical
            AVANZA = False
        End If
        '=======================================================================================================

        'CHEQUEO DEL ARCHIVO EN LA CARPETA DE DOCUMENTACIÓN TÉCNICA
        '============================================================================================================================================
        Call Rutas("DD3_ACCESS", RUTA_SALIDA, PROY_CODE)

        ITERACION = 0
        For k = 1 To 8
            REV = Chr(k + 64)
            Nombre_Ruta = RUTA_SALIDA & "DD3-" & PN_COSO_AUX(ListBox1.ListIndex + 3, ARR_COLUMNAS(2)) & "-" & REV
            Archivo_Existente_Aux = CATIA.FileSystem.FileExists(Nombre_Ruta & ".CATPart")
            If Archivo_Existente_Aux = True Then
                ITERACION = ITERACION + 1
                Archivo_Existente = True
            End If
        Next

        If Archivo_Existente = True Then
            MsgBox "El archivo existe y está liberado con letra de revisión '" & Chr(ITERACION + 64) & "', considere hacer una revisión.", vbCritical
            AVANZA = False
        End If
        '============================================================================================================================================
    
        If AVANZA = True Then

            If ListBox1.Value <> "" Then
                STR_NIV = ListBox1.Value
            Else
                STR_NIV = 0
            End If

            On Error Resume Next
            STR_CSI = PN_COSO_AUX(ListBox1.ListIndex + 3, ARR_COLUMNAS(3))
            STR_NORD = PN_COSO_AUX(ListBox1.ListIndex + 3, ARR_COLUMNAS(4))
            STR_PN = PN_COSO_AUX(ListBox1.ListIndex + 3, ARR_COLUMNAS(2))
            STR_DES = PN_COSO_AUX(ListBox1.ListIndex + 3, ARR_COLUMNAS(5))
            STR_CANT = PN_COSO_AUX(ListBox1.ListIndex + 3, ARR_COLUMNAS(9))
            STR_AUT = PN_COSO_AUX(ListBox1.ListIndex + 3, ARR_COLUMNAS(10))
            NO_CREAR = False
            On Error GoTo 0

        End If

    End If

ElseIf BOOL_MAT_PRIM = True Then

    On Error Resume Next

    STR_GRUPO = PN_COSO_AUX_2(ListBox1.ListIndex + 2, 1)
    STR_PROD_SEMI = PN_COSO_AUX_2(ListBox1.ListIndex + 2, 2)
    STR_DES_MAT = PN_COSO_AUX_2(ListBox1.ListIndex + 2, 3)
    STR_NRO_PARTE_MAT = PN_COSO_AUX_2(ListBox1.ListIndex + 2, 4)
    STR_ESTADO_TERMIC = PN_COSO_AUX_2(ListBox1.ListIndex + 2, 5)
    STR_NORM_MAT_PRIM = PN_COSO_AUX_2(ListBox1.ListIndex + 2, 6)
    STR_APP = PN_COSO_AUX_2(ListBox1.ListIndex + 2, 12)
    STR_NDP = PN_COSO_AUX_2(ListBox1.ListIndex + 2, 13)
    STR_DIM = PN_COSO_AUX_2(ListBox1.ListIndex + 2, 14)

    NO_CREAR = False
    On Error GoTo 0

    UserForm91.TextBox9.Value = STR_DES_MAT
    UserForm91.TextBox13.Value = STR_NRO_PARTE_MAT
    UserForm91.TextBox10.Value = STR_NORM_MAT_PRIM

    If STR_ESTADO_TERMIC <> "" Then
        UserForm91.TextBox11.Value = STR_ESTADO_TERMIC
        UserForm91.TextBox11.Enabled = False
    Else
        UserForm91.TextBox11.Enabled = True
        UserForm91.TextBox11.BorderColor = &H8000000D
    End If

End If

Unload UserForm9

End Sub

Private Sub CommandButton2_Click()

TextBox1.BackColor = &H80000004
Label1.Caption = ""
TextBox2.BackColor = &H80000004
Label2.Caption = ""
TextBox3.BackColor = &H80000004
Label3.Caption = ""
TextBox4.BackColor = &H80000004
Label4.Caption = ""
TextBox5.BackColor = &H80000004
Label5.Caption = ""
TextBox9.BackColor = &H80000004
Label9.Caption = ""

If Len(INPUT_COSO) <= 2 And FILTRADO = True Then
    BOOL_MAT_PRIM = False
    Call Fill(PN_COSO, BOOL_MAT_PRIM)
    FILTRADO = False
    TextBox10.Value = ""
End If

End Sub

Private Sub ListBox1_Click()


If BOOL_MAT_PRIM = False Then

    Call PROYECTO(PROY_CODE, PROYS, ARM_SYS)
    
    PROY_CODE = ComboBox1.Value 'SE PRIORIZA LA SELECCIÓN EN EL COMBOBOX POR SOBRE EL ARCHIVO QUE ESTÁ ABIERTO.
    
    Call Param_PN(ARR_PN, PROY_CODE)
    
    TextBox1.BackColor = &H8000000F
    
    BO_PART = False
    BO_PROD = False
    
    BO_ST = False
    'BO_EG = False
    
    BO_DD3 = False
    BO_PD3 = False
    BO_FV = False
    
    BO_ZG = False
    
    TextBox1.BackColor = &H80000004
    Label1.Caption = ""
    TextBox2.BackColor = &H80000004
    Label2.Caption = ""
    TextBox3.BackColor = &H80000004
    Label3.Caption = ""
    TextBox4.BackColor = &H80000004
    Label4.Caption = ""
    TextBox5.BackColor = &H80000004
    Label5.Caption = ""
    TextBox9.BackColor = &H80000004
    Label9.Caption = ""
    
    If FILTRADO = False Then
    
        If PN_COSO(ListBox1.ListIndex + 3, ARR_COLUMNAS(2)) <> "" Then
            
            REV = "A"
            'CHEQUEO DEL ARCHIVO EN LA CARPETA DE PROCESOS
            '======================================================================================================
            Call Rutas("PROCESO", RUTA_SALIDA, PROY_CODE)
            Grupo = Mid(PN_COSO(ListBox1.ListIndex + 3, ARR_COLUMNAS(2)), ARR_PN(2), 1)
            Ruta = RUTA_SALIDA & Grupo & "00\3D\"
            'MsgBox Ruta & "--" & Grupo
            
            Nombre_Ruta = Ruta & PN_COSO(ListBox1.ListIndex + 3, ARR_COLUMNAS(2)) & "_" & PN_COSO(ListBox1.ListIndex + 3, ARR_COLUMNAS(5))
            Archivo_Existente_Part = CATIA.FileSystem.FileExists(Nombre_Ruta & ".CATPart")
            Archivo_Existente_Prod = CATIA.FileSystem.FileExists(Nombre_Ruta & ".CATProduct")
            
            If Archivo_Existente_Part = True Then
                BO_PART = True
            End If
            
            If Archivo_Existente_Prod = True Then
                BO_PROD = True
            End If
            '=======================================================================================================
            
            'CHEQUEO DEL ARCHIVO EN LA CARPETA DE DOCUMENTACIÓN TÉCNICA DD3
            '============================================================================================================================================
            Call Rutas("DD3_ACCESS", RUTA_SALIDA, PROY_CODE)
            ITER_DD3 = 0
            For k = 1 To 8
                REV = Chr(k + 64)
                Nombre_Ruta = RUTA_SALIDA & "DD3-" & PN_COSO(ListBox1.ListIndex + 3, ARR_COLUMNAS(2)) & "-" & REV
                Archivo_Existente_Aux = CATIA.FileSystem.FileExists(Nombre_Ruta & ".CATPart")
                If Archivo_Existente_Aux = True Then
                    ITER_DD3 = ITER_DD3 + 1
                    BO_DD3 = True
                End If
            Next
            '============================================================================================================================================
    
            'CHEQUEO DEL ARCHIVO EN LA CARPETA DE DOCUMENTACIÓN TÉCNICA ZG, AP, BP, CC, EL, KB, LP, UP
            '============================================================================================================================================
            Call Rutas("ZG", RUTA_SALIDA, PROY_CODE)
            ITER_ZG = 0
            LABEL_2D = ""
            For k = 1 To 8
                REV = Chr(k + 64)
                Nombre_Ruta = RUTA_SALIDA & "ZG-" & PN_COSO(ListBox1.ListIndex + 3, ARR_COLUMNAS(2)) & "-" & REV
                Archivo_Existente_Aux = CATIA.FileSystem.FileExists(Nombre_Ruta & ".pdf")
                If Archivo_Existente_Aux = True Then
                    ITER_ZG = ITER_ZG + 1
                    BO_ZG = True
                    LABEL_2D = "ZG"
                End If
            Next
                
            If Archivo_Existente_Aux = False And BO_ZG = False Then
            ITER_ZG = 0
                For k = 1 To 8
                    REV = Chr(k + 64)
                    Nombre_Ruta_AP = RUTA_SALIDA & "AP-" & PN_COSO(ListBox1.ListIndex + 3, ARR_COLUMNAS(2)) & "-" & REV
                    Archivo_Existente_Aux = CATIA.FileSystem.FileExists(Nombre_Ruta_AP & ".pdf")
                    If Archivo_Existente_Aux = True Then
                        ITER_ZG = ITER_ZG + 1
                        BO_ZG = True
                        LABEL_2D = "AP"
                    End If
                Next
            End If
            
            If Archivo_Existente_Aux = False And BO_ZG = False Then
            ITER_ZG = 0
                For k = 1 To 8
                    REV = Chr(k + 64)
                    Nombre_Ruta_BP = RUTA_SALIDA & "BP-" & PN_COSO(ListBox1.ListIndex + 3, ARR_COLUMNAS(2)) & "-" & REV
                    Archivo_Existente_Aux = CATIA.FileSystem.FileExists(Nombre_Ruta_BP & ".pdf")
                    If Archivo_Existente_Aux = True Then
                        ITER_ZG = ITER_ZG + 1
                        BO_ZG = True
                        LABEL_2D = "BP"
                    End If
                Next
            End If
            
            If Archivo_Existente_Aux = False And BO_ZG = False Then
            ITER_ZG = 0
                For k = 1 To 8
                    REV = Chr(k + 64)
                    Nombre_Ruta_CC = RUTA_SALIDA & "CC-" & PN_COSO(ListBox1.ListIndex + 3, ARR_COLUMNAS(2)) & "-" & REV
                    Archivo_Existente_Aux = CATIA.FileSystem.FileExists(Nombre_Ruta_CC & ".pdf")
                    If Archivo_Existente_Aux = True Then
                        ITER_ZG = ITER_ZG + 1
                        BO_ZG = True
                        LABEL_2D = "CC"
                    End If
                Next
            End If
            
            If Archivo_Existente_Aux = False And BO_ZG = False Then
            ITER_ZG = 0
                For k = 1 To 8
                    REV = Chr(k + 64)
                    Nombre_Ruta_EL = RUTA_SALIDA & "EL-" & PN_COSO(ListBox1.ListIndex + 3, ARR_COLUMNAS(2)) & "-" & REV
                    Archivo_Existente_Aux = CATIA.FileSystem.FileExists(Nombre_Ruta_EL & ".pdf")
                    If Archivo_Existente_Aux = True Then
                        ITER_ZG = ITER_ZG + 1
                        BO_ZG = True
                        LABEL_2D = "EL"
                    End If
                Next
            End If
            
            If Archivo_Existente_Aux = False And BO_ZG = False Then
            ITER_ZG = 0
                For k = 1 To 8
                    REV = Chr(k + 64)
                    Nombre_Ruta_KB = RUTA_SALIDA & "KB-" & PN_COSO(ListBox1.ListIndex + 3, ARR_COLUMNAS(2)) & "-" & REV
                    Archivo_Existente_Aux = CATIA.FileSystem.FileExists(Nombre_Ruta_KB & ".pdf")
                    If Archivo_Existente_Aux = True Then
                        ITER_ZG = ITER_ZG + 1
                        BO_ZG = True
                        LABEL_2D = "KB"
                    End If
                Next
            End If
            
            If Archivo_Existente_Aux = False And BO_ZG = False Then
            ITER_ZG = 0
                For k = 1 To 8
                    REV = Chr(k + 64)
                    Nombre_Ruta_LP = RUTA_SALIDA & "LP-" & PN_COSO(ListBox1.ListIndex + 3, ARR_COLUMNAS(2)) & "-" & REV
                    Archivo_Existente_Aux = CATIA.FileSystem.FileExists(Nombre_Ruta_LP & ".pdf")
                    If Archivo_Existente_Aux = True Then
                        ITER_ZG = ITER_ZG + 1
                        BO_ZG = True
                        LABEL_2D = "LP"
                    End If
                Next
            End If
            
            If Archivo_Existente_Aux = False And BO_ZG = False Then
            ITER_ZG = 0
                For k = 1 To 8
                    REV = Chr(k + 64)
                    Nombre_Ruta_UP = RUTA_SALIDA & "UP-" & PN_COSO(ListBox1.ListIndex + 3, ARR_COLUMNAS(2)) & "-" & REV
                    Archivo_Existente_Aux = CATIA.FileSystem.FileExists(Nombre_Ruta_UP & ".pdf")
                    If Archivo_Existente_Aux = True Then
                        ITER_ZG = ITER_ZG + 1
                        BO_ZG = True
                        LABEL_2D = "UP"
                    End If
                Next
            End If
            
            '============================================================================================================================================
            
            'CHEQUEO DEL ARCHIVO EN LA CARPETA DE DOCUMENTACIÓN TÉCNICA ST
            '============================================================================================================================================
            Call Rutas("ST", RUTA_SALIDA, PROY_CODE)
            ITER_ST = 0
            For k = 1 To 8
                REV = Chr(k + 64)
                Nombre_Ruta = RUTA_SALIDA & "ST-" & PN_COSO(ListBox1.ListIndex + 3, ARR_COLUMNAS(2)) & "-" & REV
                Archivo_Existente_Aux = CATIA.FileSystem.FileExists(Nombre_Ruta & ".pdf")
                If Archivo_Existente_Aux = True Then
                    ITER_ST = ITER_ST + 1
                    BO_ST = True
                    LABEL_ST = "ST"
                End If
            Next
            
            If Archivo_Existente_Aux = False And BO_ST = False Then
                For k = 1 To 8
                    REV = Chr(k + 64)
                    Nombre_Ruta_EG = RUTA_SALIDA & "EG-" & PN_COSO(ListBox1.ListIndex + 3, ARR_COLUMNAS(2)) & "-" & REV
                    Archivo_Existente_Aux = CATIA.FileSystem.FileExists(Nombre_Ruta_EG & ".pdf")
                    If Archivo_Existente_Aux = True Then
                        ITER_ST = ITER_ST + 1
                        BO_ST = True
                        LABEL_ST = "EG"
                    End If
                Next
            End If
            
            
            '============================================================================================================================================
                    
            'CHEQUEO DEL ARCHIVO EN LA CARPETA DE DOCUMENTACIÓN TÉCNICA PD3
            '============================================================================================================================================
            Call Rutas("PD3", RUTA_SALIDA, PROY_CODE)
            ITER_PD3 = 0
            For k = 1 To 8
                REV = Chr(k + 64)
                Nombre_Ruta = RUTA_SALIDA & "PD3-" & PN_COSO(ListBox1.ListIndex + 3, ARR_COLUMNAS(2)) & "-" & REV
                Archivo_Existente_Aux = CATIA.FileSystem.FileExists(Nombre_Ruta & ".pdf")
                If Archivo_Existente_Aux = True Then
                    ITER_PD3 = ITER_PD3 + 1
                    BO_PD3 = True
                End If
            Next
            '============================================================================================================================================
            
            'CHEQUEO DEL ARCHIVO EN LA CARPETA DE DOCUMENTACIÓN TÉCNICA FV
            '============================================================================================================================================
            Call Rutas("FV", RUTA_SALIDA, PROY_CODE)
            ITER_FV = 0
            For k = 1 To 8
                REV = Chr(k + 64)
                Nombre_Ruta = RUTA_SALIDA & "FV-" & PN_COSO(ListBox1.ListIndex + 3, ARR_COLUMNAS(2)) & "-" & REV
                Archivo_Existente_Aux = CATIA.FileSystem.FileExists(Nombre_Ruta & ".pdf")
                If Archivo_Existente_Aux = True Then
                    ITER_FV = ITER_FV + 1
                    BO_FV = True
                End If
            Next
            '============================================================================================================================================
            
            If BO_ZG = True Then
                 TextBox1.BackColor = &HFF00&
                 Label1.Caption = Chr(ITER_ZG + 64)
            End If
            If BO_ST = True Then
                 TextBox2.BackColor = &HFF00&
                 Label2.Caption = Chr(ITER_ST + 64)
            End If
            If BO_DD3 = True Then
                 TextBox3.BackColor = &HFF00&
                 Label3.Caption = Chr(ITER_DD3 + 64)
            End If
            If BO_PD3 = True Then
                 TextBox4.BackColor = &HFF00&
                 Label4.Caption = Chr(ITER_PD3 + 64)
            End If
            If BO_FV = True Then
                 TextBox5.BackColor = &HFF00&
                 Label5.Caption = Chr(ITER_FV + 64)
            End If
            
        SALTA = False
            
            If BO_PART = True Then 'SI LA PARTE EXISTE EN LA CARPETA DE INGENIERÍA
                TextBox9.BackColor = &HFF00&
                Label9.Caption = "EDITABLE"
                LABEL_2D = "ZG"
            ElseIf BO_PART = False And (BO_ST = True Or BO_DD3 = True Or BO_PD3 = True Or BO_FV = True) Then 'SI NO EXISTE LA PARTE EN LA CARPETA DE INGENIERÍA, PERO ESTA LIBERADA
                TextBox9.BackColor = &HFF&
                Label9.Caption = "REQUIERE REVISIÓN PARA SER MODIFICADO"
                LABEL_2D = "ZG"
                SALTA = True
            End If
            
            If BO_PROD = True And (BO_ST = True Or BO_ZG = True) Then 'SI EXISTE PRODUCTO EN LA CARPETA DE INGENIERÍA Y EXISTE ST Y ZG EN DOC TECNICA
                TextBox9.BackColor = &HFFFF&
                Label9.Caption = "EDITABLE, REQUIERE REVISIÓN PARA SER MODIFICADO"
            ElseIf BO_PROD = True And (BO_ST = False Or BO_DD3 = False) Then 'SI EXISTE PRODUCTO EN LA CARPETA DE INGENIERÍA Y NO EXISTE NADA EN DOC TECNICA
                TextBox9.BackColor = &HFF00&
                Label9.Caption = "EDITABLE"
                LABEL_2D = "ZG"
            ElseIf BO_PROD = False And (BO_ST = True Or BO_ZG = True) Then 'SI NO EXISTE PRODUCTO EN LA CARPETA DE INGENIERÍA (Y NO EXISTE DD3, FV O PD3 [ESTOS SERÍAN PARTES])
                TextBox9.BackColor = &HFF&
                Label9.Caption = "EL ARCHIVO NO SE ENCUENTRA"
            End If
            
            If BO_PROD = False And BO_PART = False And SALTA = False Then 'SI NO EXISTE PARTE Y NO EXITE PRODUCTO EN LA CARPETA DE INGENIERÍA
                TextBox9.BackColor = &H80FF&
                Label9.Caption = "NO CREADO"
                LABEL_2D = "ZG"
            End If
            
        Else
            Label1.Caption = ""
            TextBox1.BackColor = &H8000000F
            LABEL_2D = "ZG"
        End If
    
    ElseIf FILTRADO = True Then
    
        If PN_COSO_AUX(ListBox1.ListIndex + 3, ARR_COLUMNAS(2)) <> "" Then
             
    'ARR_COLUMNAS (1) 'NIVEL
    'ARR_COLUMNAS (3) 'CSI
    'ARR_COLUMNAS (4) 'NRO_ORD
    'ARR_COLUMNAS (2) 'NRO_PARTE
    'ARR_COLUMNAS (5) 'DES
    'ARR_COLUMNAS (6) 'TEC
    'ARR_COLUMNAS (9) 'CANT
    'ARR_COLUMNAS (10) 'AUTOR
    'ARR_COLUMNAS (8) 'MAT
    
            REV = "A"
            'CHEQUEO DEL ARCHIVO EN LA CARPETA DE PROCESOS
            '======================================================================================================
            Call Rutas("PROCESO", RUTA_SALIDA, PROY_CODE)
            Grupo = Mid(PN_COSO_AUX(ListBox1.ListIndex + 3, ARR_COLUMNAS(2)), ARR_PN(2), 1)
            Ruta = RUTA_SALIDA & Grupo & "00\3D\"
            Nombre_Ruta = Ruta & PN_COSO_AUX(ListBox1.ListIndex + 3, ARR_COLUMNAS(2)) & "_" & PN_COSO_AUX(ListBox1.ListIndex + 3, ARR_COLUMNAS(5))
            Archivo_Existente_Part = CATIA.FileSystem.FileExists(Nombre_Ruta & ".CATPart")
            Archivo_Existente_Prod = CATIA.FileSystem.FileExists(Nombre_Ruta & ".CATProduct")
            
            If Archivo_Existente_Part = True Then
                BO_PART = True
            End If
            
            If Archivo_Existente_Prod = True Then
                BO_PROD = True
            End If
            '=======================================================================================================
            
            'CHEQUEO DEL ARCHIVO EN LA CARPETA DE DOCUMENTACIÓN TÉCNICA DD3
            '============================================================================================================================================
            Call Rutas("DD3_ACCESS", RUTA_SALIDA, PROY_CODE)
            ITER_DD3 = 0
            For k = 1 To 8
                REV = Chr(k + 64)
                Nombre_Ruta = RUTA_SALIDA & "DD3-" & PN_COSO_AUX(ListBox1.ListIndex + 3, ARR_COLUMNAS(2)) & "-" & REV
                Archivo_Existente_Aux = CATIA.FileSystem.FileExists(Nombre_Ruta & ".CATPart")
                If Archivo_Existente_Aux = True Then
                    ITER_DD3 = ITER_DD3 + 1
                    BO_DD3 = True
                End If
            Next
            '============================================================================================================================================
            
            'CHEQUEO DEL ARCHIVO EN LA CARPETA DE DOCUMENTACIÓN TÉCNICA ZG, AP, BP, CC, EL, KB, LP, UP
            '============================================================================================================================================
            Call Rutas("ZG", RUTA_SALIDA, PROY_CODE)
            ITER_ZG = 0
            LABEL_2D = ""
            For k = 1 To 8
                REV = Chr(k + 64)
                Nombre_Ruta = RUTA_SALIDA & "ZG-" & PN_COSO_AUX(ListBox1.ListIndex + 3, ARR_COLUMNAS(2)) & "-" & REV
                Archivo_Existente_Aux = CATIA.FileSystem.FileExists(Nombre_Ruta & ".pdf")
                If Archivo_Existente_Aux = True Then
                    ITER_ZG = ITER_ZG + 1
                    BO_ZG = True
                    LABEL_2D = "ZG"
                End If
            Next
                
            If Archivo_Existente_Aux = False And BO_ZG = False Then
            ITER_ZG = 0
                For k = 1 To 8
                    REV = Chr(k + 64)
                    Nombre_Ruta_AP = RUTA_SALIDA & "AP-" & PN_COSO_AUX(ListBox1.ListIndex + 3, ARR_COLUMNAS(2)) & "-" & REV
                    Archivo_Existente_Aux = CATIA.FileSystem.FileExists(Nombre_Ruta_AP & ".pdf")
                    If Archivo_Existente_Aux = True Then
                        ITER_ZG = ITER_ZG + 1
                        BO_ZG = True
                        LABEL_2D = "AP"
                    End If
                Next
            End If
            
            If Archivo_Existente_Aux = False And BO_ZG = False Then
            ITER_ZG = 0
                For k = 1 To 8
                    REV = Chr(k + 64)
                    Nombre_Ruta_BP = RUTA_SALIDA & "BP-" & PN_COSO_AUX(ListBox1.ListIndex + 3, ARR_COLUMNAS(2)) & "-" & REV
                    Archivo_Existente_Aux = CATIA.FileSystem.FileExists(Nombre_Ruta_BP & ".pdf")
                    If Archivo_Existente_Aux = True Then
                        ITER_ZG = ITER_ZG + 1
                        BO_ZG = True
                        LABEL_2D = "BP"
                    End If
                Next
            End If
            
            If Archivo_Existente_Aux = False And BO_ZG = False Then
            ITER_ZG = 0
                For k = 1 To 8
                    REV = Chr(k + 64)
                    Nombre_Ruta_CC = RUTA_SALIDA & "CC-" & PN_COSO_AUX(ListBox1.ListIndex + 3, ARR_COLUMNAS(2)) & "-" & REV
                    Archivo_Existente_Aux = CATIA.FileSystem.FileExists(Nombre_Ruta_CC & ".pdf")
                    If Archivo_Existente_Aux = True Then
                        ITER_ZG = ITER_ZG + 1
                        BO_ZG = True
                        LABEL_2D = "CC"
                    End If
                Next
            End If
            
            If Archivo_Existente_Aux = False And BO_ZG = False Then
            ITER_ZG = 0
                For k = 1 To 8
                    REV = Chr(k + 64)
                    Nombre_Ruta_EL = RUTA_SALIDA & "EL-" & PN_COSO_AUX(ListBox1.ListIndex + 3, ARR_COLUMNAS(2)) & "-" & REV
                    Archivo_Existente_Aux = CATIA.FileSystem.FileExists(Nombre_Ruta_EL & ".pdf")
                    If Archivo_Existente_Aux = True Then
                        ITER_ZG = ITER_ZG + 1
                        BO_ZG = True
                        LABEL_2D = "EL"
                    End If
                Next
            End If
            
            If Archivo_Existente_Aux = False And BO_ZG = False Then
            ITER_ZG = 0
                For k = 1 To 8
                    REV = Chr(k + 64)
                    Nombre_Ruta_KB = RUTA_SALIDA & "KB-" & PN_COSO_AUX(ListBox1.ListIndex + 3, ARR_COLUMNAS(2)) & "-" & REV
                    Archivo_Existente_Aux = CATIA.FileSystem.FileExists(Nombre_Ruta_KB & ".pdf")
                    If Archivo_Existente_Aux = True Then
                        ITER_ZG = ITER_ZG + 1
                        BO_ZG = True
                        LABEL_2D = "KB"
                    End If
                Next
            End If
            
            If Archivo_Existente_Aux = False And BO_ZG = False Then
            ITER_ZG = 0
                For k = 1 To 8
                    REV = Chr(k + 64)
                    Nombre_Ruta_LP = RUTA_SALIDA & "LP-" & PN_COSO_AUX(ListBox1.ListIndex + 3, ARR_COLUMNAS(2)) & "-" & REV
                    Archivo_Existente_Aux = CATIA.FileSystem.FileExists(Nombre_Ruta_LP & ".pdf")
                    If Archivo_Existente_Aux = True Then
                        ITER_ZG = ITER_ZG + 1
                        BO_ZG = True
                        LABEL_2D = "LP"
                    End If
                Next
            End If
            
            If Archivo_Existente_Aux = False And BO_ZG = False Then
            ITER_ZG = 0
                For k = 1 To 8
                    REV = Chr(k + 64)
                    Nombre_Ruta_UP = RUTA_SALIDA & "UP-" & PN_COSO_AUX(ListBox1.ListIndex + 3, ARR_COLUMNAS(2)) & "-" & REV
                    Archivo_Existente_Aux = CATIA.FileSystem.FileExists(Nombre_Ruta_UP & ".pdf")
                    If Archivo_Existente_Aux = True Then
                        ITER_ZG = ITER_ZG + 1
                        BO_ZG = True
                        LABEL_2D = "UP"
                    End If
                Next
            End If
            
            '============================================================================================================================================
            
            'CHEQUEO DEL ARCHIVO EN LA CARPETA DE DOCUMENTACIÓN TÉCNICA ST
            '============================================================================================================================================
            Call Rutas("ST", RUTA_SALIDA, PROY_CODE)
            ITER_ST = 0
            For k = 1 To 8
                REV = Chr(k + 64)
                Nombre_Ruta = RUTA_SALIDA & "ST-" & PN_COSO_AUX(ListBox1.ListIndex + 3, ARR_COLUMNAS(2)) & "-" & REV
                Archivo_Existente_Aux = CATIA.FileSystem.FileExists(Nombre_Ruta & ".pdf")
                If Archivo_Existente_Aux = True Then
                    ITER_ST = ITER_ST + 1
                    BO_ST = True
                    LABEL_ST = "ST"
                End If
            Next
            
            If Archivo_Existente_Aux = False And BO_ST = False Then
                For k = 1 To 8
                    REV = Chr(k + 64)
                    Nombre_Ruta_EG = RUTA_SALIDA & "EG-" & PN_COSO_AUX(ListBox1.ListIndex + 3, ARR_COLUMNAS(2)) & "-" & REV
                    Archivo_Existente_Aux = CATIA.FileSystem.FileExists(Nombre_Ruta_EG & ".pdf")
                    If Archivo_Existente_Aux = True Then
                        ITER_ST = ITER_ST + 1
                        BO_ST = True
                        LABEL_ST = "EG"
                    End If
                Next
            End If
            
            
            '============================================================================================================================================
                    
            'CHEQUEO DEL ARCHIVO EN LA CARPETA DE DOCUMENTACIÓN TÉCNICA PD3
            '============================================================================================================================================
            Call Rutas("PD3", RUTA_SALIDA, PROY_CODE)
            ITER_PD3 = 0
            For k = 1 To 8
                REV = Chr(k + 64)
                Nombre_Ruta = RUTA_SALIDA & "PD3-" & PN_COSO_AUX(ListBox1.ListIndex + 3, ARR_COLUMNAS(2)) & "-" & REV
                Archivo_Existente_Aux = CATIA.FileSystem.FileExists(Nombre_Ruta & ".pdf")
                If Archivo_Existente_Aux = True Then
                    ITER_PD3 = ITER_PD3 + 1
                    BO_PD3 = True
                End If
            Next
            '============================================================================================================================================
            
            'CHEQUEO DEL ARCHIVO EN LA CARPETA DE DOCUMENTACIÓN TÉCNICA FV
            '============================================================================================================================================
            Call Rutas("FV", RUTA_SALIDA, PROY_CODE)
            ITER_FV = 0
            For k = 1 To 8
                REV = Chr(k + 64)
                Nombre_Ruta = RUTA_SALIDA & "FV-" & PN_COSO_AUX(ListBox1.ListIndex + 3, ARR_COLUMNAS(2)) & "-" & REV
                Archivo_Existente_Aux = CATIA.FileSystem.FileExists(Nombre_Ruta & ".pdf")
                If Archivo_Existente_Aux = True Then
                    ITER_FV = ITER_FV + 1
                    BO_FV = True
                End If
            Next
            '============================================================================================================================================
            
            If BO_ZG = True Then
                 TextBox1.BackColor = &HFF00&
                 Label1.Caption = Chr(ITER_ZG + 64)
            End If
            If BO_ST = True Then
                 TextBox2.BackColor = &HFF00&
                 Label2.Caption = Chr(ITER_ST + 64)
            End If
            If BO_DD3 = True Then
                 TextBox3.BackColor = &HFF00&
                 Label3.Caption = Chr(ITER_DD3 + 64)
            End If
            If BO_PD3 = True Then
                 TextBox4.BackColor = &HFF00&
                 Label4.Caption = Chr(ITER_PD3 + 64)
            End If
            If BO_FV = True Then
                 TextBox5.BackColor = &HFF00&
                 Label5.Caption = Chr(ITER_FV + 64)
            End If
            
        SALTA = False
            
            If BO_PART = True Then 'SI LA PARTE EXISTE EN LA CARPETA DE INGENIERÍA
                TextBox9.BackColor = &HFF00&
                Label9.Caption = "EDITABLE"
                LABEL_2D = "ZG"
            ElseIf BO_PART = False And (BO_ST = True Or BO_DD3 = True Or BO_PD3 = True Or BO_FV = True) Then 'SI NO EXISTE LA PARTE EN LA CARPETA DE INGENIERÍA, PERO ESTA LIBERADA
                TextBox9.BackColor = &HFF&
                Label9.Caption = "REQUIERE REVISIÓN PARA SER MODIFICADO"
                LABEL_2D = "ZG"
                SALTA = True
            End If
            
            If BO_PROD = True And (BO_ST = True Or BO_ZG = True) Then 'SI EXISTE PRODUCTO EN LA CARPETA DE INGENIERÍA Y EXISTE ST Y ZG EN DOC TECNICA
                TextBox9.BackColor = &HFFFF&
                Label9.Caption = "EDITABLE, REQUIERE REVISIÓN PARA SER MODIFICADO"
            ElseIf BO_PROD = True And (BO_ST = False Or BO_DD3 = False) Then 'SI EXISTE PRODUCTO EN LA CARPETA DE INGENIERÍA Y NO EXISTE NADA EN DOC TECNICA
                TextBox9.BackColor = &HFF00&
                Label9.Caption = "EDITABLE"
                LABEL_2D = "ZG"
            ElseIf BO_PROD = False And (BO_ST = True Or BO_ZG = True) Then 'SI NO EXISTE PRODUCTO EN LA CARPETA DE INGENIERÍA (Y NO EXISTE DD3, FV O PD3 [ESTOS SERÍAN PARTES])
                TextBox9.BackColor = &HFF&
                Label9.Caption = "EL ARCHIVO NO SE ENCUENTRA"
            End If
            
            If BO_PROD = False And BO_PART = False And SALTA = False Then 'SI NO EXISTE PARTE Y NO EXITE PRODUCTO EN LA CARPETA DE INGENIERÍA
                TextBox9.BackColor = &H80FF&
                Label9.Caption = "NO CREADO"
                LABEL_2D = "ZG"
            End If
            
        Else
            Label1.Caption = ""
            TextBox1.BackColor = &H8000000F
            LABEL_2D = "ZG"
        End If
    
    End If
    
    Frame1.Caption = LABEL_2D

ElseIf BOOL_MAT_PRIM = True Then

End If

End Sub

Private Sub TextBox10_Change()

ReDim PN_COSO_AUX(0 To 3000, 0 To 20) As Variant

PROY_CODE = ComboBox1.Value 'SE PRIORIZA LA SELECCIÓN EN EL COMBOBOX POR SOBRE EL ARCHIVO QUE ESTÁ ABIERTO.
Call Columnas_EP(ARR_COLUMNAS, COL_LIMITE, PROY_CODE)
'ARR_COLUMNAS (1) 'NIVEL
'ARR_COLUMNAS (3) 'CSI
'ARR_COLUMNAS (4) 'NRO_ORD
'ARR_COLUMNAS (2) 'NRO_PARTE
'ARR_COLUMNAS (5) 'DES
'ARR_COLUMNAS (6) 'TEC
'ARR_COLUMNAS (9) 'CANT
'ARR_COLUMNAS (10) 'AUTOR
'ARR_COLUMNAS (8) 'MAT

Call Param_PN(ARR_PN, PROY_CODE)

Dim INPUT_COSO As String

INPUT_COSO = TextBox10.Value

If Len(INPUT_COSO) > 2 Then
    
    TextBox1.BackColor = &H80000004
    Label1.Caption = ""
    TextBox2.BackColor = &H80000004
    Label2.Caption = ""
    TextBox3.BackColor = &H80000004
    Label3.Caption = ""
    TextBox4.BackColor = &H80000004
    Label4.Caption = ""
    TextBox5.BackColor = &H80000004
    Label5.Caption = ""
    TextBox9.BackColor = &H80000004
    Label9.Caption = ""
    
    'se obtiene la cantidad de elementos para redimensionar la matriz
    FILA_FILTRO = 0
    For i = 1 To UBound(PN_COSO, 1)
        If InStr(1, PN_COSO(i, ARR_COLUMNAS(2)), INPUT_COSO, 1) > 1 Then
        FILA_FILTRO = FILA_FILTRO + 1
        End If
    Next
    
    ReDim PN_COSO_AUX(0 To FILA_FILTRO, 0 To COL_LIMITE) As Variant 'se redimensiona la matriz
    
    'se llena la matriz de elmentos
    j = 0
    For i = 1 To UBound(PN_COSO, 1)
        If InStr(1, PN_COSO(i, ARR_COLUMNAS(2)), INPUT_COSO, 1) > 1 Then
            j = j + 1
                For k = 1 To UBound(PN_COSO, 2)
                    PN_COSO_AUX(j, k) = PN_COSO(i, k)
                Next
        End If
    Next
    
    If FILA_FILTRO > 0 Then
        BOOL_MAT_PRIM = False
        Call Fill(PN_COSO_AUX, BOOL_MAT_PRIM)
    End If

    FILTRADO = True

End If

End Sub
Private Sub ComboBox1_Change()

    If bMakeItHappen Then
        BOOL_MAT_PRIM = False
        Call Lectura(PN_COSO, ComboBox1.Value)
        Call Fill(PN_COSO, BOOL_MAT_PRIM)
    
        For i = 1 To LBound(PROYS)
            If ComboBox1.Value = PROYS(1) Then
                ListBox2.BackColor = RGB(126, 162, 151)
            End If
            If ComboBox1.Value = PROYS(2) Then
                ListBox2.BackColor = RGB(128, 255, 0)
            End If
            If ComboBox1.Value = PROYS(3) Then
                ListBox2.BackColor = RGB(131, 170, 214)
            End If
'            If PROY_CODE = PROYS(4) Then
'                ListBox2.BackColor = RGB(126, 162, 151)
'            End If
'            If PROY_CODE = PROYS(5) Then
'                ListBox2.BackColor = RGB(126, 162, 151)
'            End If
'            If PROY_CODE = PROYS(6) Then
'                ListBox2.BackColor = RGB(126, 162, 151)
'            End If
        Next
    
    End If

End Sub

Private Sub ComboBox1_DropButtonClick()
    bMakeItHappen = True
End Sub
Private Sub UserForm_Initialize()

UserForm9.Width = 1046

If BOOL_MAT_PRIM = False Then

    If BOOL_BLOCK_MAT_PRIM = True Then
        CheckBox1.Visible = False
    ElseIf BOOL_BLOCK_MAT_PRIM = False Then
        CheckBox1.Visible = True
    End If
    
    Call PROYECTO(PROY_CODE, PROYS, ARM_SYS)
    
    For i = 1 To LBound(PROYS)
        If PROY_CODE = PROYS(1) Then
            ListBox2.BackColor = RGB(126, 162, 151)
        End If
        If PROY_CODE = PROYS(2) Then
            ListBox2.BackColor = RGB(126, 162, 151)
        End If
        If PROY_CODE = PROYS(3) Then
            ListBox2.BackColor = RGB(131, 170, 214)
        End If
    '    If PROY_CODE = PROYS(4) Then
    '        ListBox2.BackColor = RGB(126, 162, 151)
    '    End If
    '    If PROY_CODE = PROYS(5) Then
    '        ListBox2.BackColor = RGB(126, 162, 151)
    '    End If
    '    If PROY_CODE = PROYS(6) Then
    '        ListBox2.BackColor = RGB(126, 162, 151)
    '    End If
    Next
    
    For i = 1 To UBound(PROYS)
        ComboBox1.AddItem PROYS(i)
    Next
    
    BOOL_MAT_PRIM = False
    Call Lectura(PN_COSO, PROY_CODE)
    Call Fill(PN_COSO, BOOL_MAT_PRIM)
    
ElseIf BOOL_MAT_PRIM = True Then

    CheckBox1.Visible = False
    ComboBox1.Enabled = False
    Frame12.Visible = False
    Frame13.Visible = False
    Frame6.Visible = False
    Frame7.Visible = False
    Frame14.Visible = False
    
    BOOL_MAT_PRIM = True
    Call Lectura_Mat(PN_COSO_AUX_2, ComboBox1.Value)
    Call Fill(PN_COSO_AUX_2, BOOL_MAT_PRIM)

End If

End Sub

Private Sub Fill(Matriz, BOOL_MAT_PRIM)

Call Columnas_EP(ARR_COLUMNAS, COL_LIMITE, ComboBox1.Value)

ListBox1.Clear
ListBox2.Clear

If BOOL_MAT_PRIM = False Then

    NIVEL_ANCHO = 45
    CSI_ANCHO = 120
    NRO_ORD_ANCHO = 70
    NRO_PARTE_ANCHO = 140
    DES_ANCHO = 230
    TEC_ANCHO = 170
    CANT_ANCHO = 55
    AUTOR_ANCHO = 90
    MAT_ANCHO = 80
    
    ANCHO_TOTAL = NIVEL_ANCHO + CSI_ANCHO + NRO_ORD_ANCHO + NRO_PARTE_ANCHO + DES_ANCHO + TEC_ANCHO + CANT_ANCHO + AUTOR_ANCHO + MAT_ANCHO
    
    'SE ESTABLECE UN VALOR QUE NO AFECTE LA DIMENSION
    '================================================
    NIVEL_ANCHO_2 = 1
    CSI_ANCHO_2 = 1
    NRO_ORD_ANCHO_2 = 1
    NRO_PARTE_ANCHO_2 = 1
    DES_ANCHO_2 = 1
    TEC_ANCHO_2 = 1
    CANT_ANCHO_2 = 1
    AUTOR_ANCHO_2 = 1
    MAT_ANCHO_2 = 1
    
    'SE ANULA LA COLUMNA SI ESTA NO EXISTE PARA EL PROYECTO
    '======================================================
    COL = 9
    If ARR_COLUMNAS(1) = 0 Then 'NIVEL
        NIVEL_ANCHO_2 = 0
        COL = COL - 1
    End If
    If ARR_COLUMNAS(3) = 0 Then 'CSI
        CSI_ANCHO_2 = 0
        COL = COL - 1
    End If
    If ARR_COLUMNAS(4) = 0 Then 'NRO ORDEN
        NRO_ORD_ANCHO_2 = 0
        COL = COL - 1
    End If
    If ARR_COLUMNAS(2) = 0 Then 'PN
        NRO_PARTE_ANCHO_2 = 0
        COL = COL - 1
    End If
    If ARR_COLUMNAS(5) = 0 Then 'DESIGNACION
        DES_ANCHO_2 = 0
        COL = COL - 1
    End If
    If ARR_COLUMNAS(6) = 0 Then 'TIPO
        TEC_ANCHO_2 = 0
        COL = COL - 1
    End If
    If ARR_COLUMNAS(9) = 0 Then 'CANTIDAD
        CANT_ANCHO_2 = 0
        COL = COL - 1
    End If
    If ARR_COLUMNAS(10) = 0 Then 'DISEŃADOR
        AUTOR_ANCHO_2 = 0
        COL = COL - 1
    End If
    If ARR_COLUMNAS(8) = 0 Then 'MATERIAL
        MAT_ANCHO_2 = 0
        COL = COL - 1
    End If
    
    ANCHO_TOTAL_2 = NIVEL_ANCHO * NIVEL_ANCHO_2 + CSI_ANCHO * CSI_ANCHO_2 + NRO_ORD_ANCHO * NRO_ORD_ANCHO_2 + NRO_PARTE_ANCHO * NRO_PARTE_ANCHO_2 _
    + DES_ANCHO * DES_ANCHO_2 + TEC_ANCHO * TEC_ANCHO_2 + CANT_ANCHO * CANT_ANCHO_2 + AUTOR_ANCHO * AUTOR_ANCHO_2 + MAT_ANCHO * MAT_ANCHO_2
    
    PROP = ANCHO_TOTAL / ANCHO_TOTAL_2
    
'    STR_WIDTH = NIVEL_ANCHO * NIVEL_ANCHO_2 * PROP & ";" & CSI_ANCHO * CSI_ANCHO_2 * PROP & ";" & NRO_ORD_ANCHO * NRO_ORD_ANCHO_2 * PROP & ";" & _
'    NRO_PARTE_ANCHO * NRO_PARTE_ANCHO_2 * PROP & ";" & DES_ANCHO * DES_ANCHO_2 * PROP & ";" & TEC_ANCHO * TEC_ANCHO_2 * PROP & ";" & _
'    CANT_ANCHO * CANT_ANCHO_2 * PROP & ";" & AUTOR_ANCHO * AUTOR_ANCHO_2 * PROP & ";" & MAT_ANCHO * MAT_ANCHO_2 * PROP
    
    STR_WIDTH = CInt(NIVEL_ANCHO * NIVEL_ANCHO_2 * PROP) & ";" & CInt(CSI_ANCHO * CSI_ANCHO_2 * PROP) & ";" & CInt(NRO_ORD_ANCHO * NRO_ORD_ANCHO_2 * PROP) & ";" & _
    CInt(NRO_PARTE_ANCHO * NRO_PARTE_ANCHO_2 * PROP) & ";" & CInt(DES_ANCHO * DES_ANCHO_2 * PROP) & ";" & CInt(TEC_ANCHO * TEC_ANCHO_2 * PROP) & ";" & _
    CInt(CANT_ANCHO * CANT_ANCHO_2 * PROP) & ";" & CInt(AUTOR_ANCHO * AUTOR_ANCHO_2 * PROP) & ";" & CInt(MAT_ANCHO * MAT_ANCHO_2 * PROP)
    
    On Error GoTo 0
    ListBox1.ColumnWidths = STR_WIDTH
    ListBox1.Width = UserForm9.Width - 26
    ListBox1.ColumnCount = COL
    'Populate the listbox.
    With Me.ListBox1
        it = 0
        For i = 3 To UBound(Matriz, 1)
            'Use .AddItem property to add a new row for each record and populate column 0
            If ARR_COLUMNAS(1) <> 0 Then
                .AddItem Matriz(i, ARR_COLUMNAS(1)) 'NIVEL
            Else
                .AddItem "--"
            End If
            'Use .List method to populate the remaining columns
            If ARR_COLUMNAS(3) <> 0 Then
                .List(.ListCount - 1, 1) = Matriz(i, ARR_COLUMNAS(3)) 'CSI
            End If
            If ARR_COLUMNAS(4) <> 0 Then
                .List(.ListCount - 1, 2) = Matriz(i, ARR_COLUMNAS(4)) 'NRO. ORD.
            End If
            If ARR_COLUMNAS(2) <> 0 Then
                .List(.ListCount - 1, 3) = Matriz(i, ARR_COLUMNAS(2)) 'NRO. DE PARTE
            End If
            If ARR_COLUMNAS(5) <> 0 Then
                .List(.ListCount - 1, 4) = Matriz(i, ARR_COLUMNAS(5)) 'DESIGNACIÓN
            End If
            If ARR_COLUMNAS(6) <> 0 Then
                .List(.ListCount - 1, 5) = Matriz(i, ARR_COLUMNAS(6)) 'TECNOLOGÍA
            End If
            If ARR_COLUMNAS(9) <> 0 Then
                .List(.ListCount - 1, 6) = Matriz(i, ARR_COLUMNAS(9)) 'CANT.
            End If
            If ARR_COLUMNAS(10) <> 0 Then
                .List(.ListCount - 1, 7) = Matriz(i, ARR_COLUMNAS(10)) 'AUTOR
            End If
            If ARR_COLUMNAS(8) <> 0 Then
                .List(.ListCount - 1, 8) = Matriz(i, ARR_COLUMNAS(8)) 'MATERIAL
            End If
            
            If Matriz(i, ARR_COLUMNAS(2)) = "" Then
                it = it + 1
            Else
                it = 0
            End If
            
            If it = 40 Then
                Exit For
            End If
        
        Next i
    End With
    
    
    ListBox2.ColumnWidths = ListBox1.ColumnWidths
    ListBox2.Width = ListBox1.Width
    ListBox2.ColumnCount = COL
    'Populate the listbox.
    With Me.ListBox2
        If ARR_COLUMNAS(1) <> 0 Then
            .AddItem "NIVEL"
        Else
            .AddItem "--"
        End If
        'Use .List method to populate the remaining columns
        If ARR_COLUMNAS(3) <> 0 Then
            .List(.ListCount - 1, 1) = "CSI"
        End If
        If ARR_COLUMNAS(4) <> 0 Then
            .List(.ListCount - 1, 2) = "NRO. ORD."
        End If
        If ARR_COLUMNAS(2) <> 0 Then
            .List(.ListCount - 1, 3) = "NRO. DE PARTE"
        End If
        If ARR_COLUMNAS(5) <> 0 Then
            .List(.ListCount - 1, 4) = "DESIGNACIÓN"
        End If
        If ARR_COLUMNAS(6) <> 0 Then
            .List(.ListCount - 1, 5) = "TECNOLOGÍA"
        End If
        If ARR_COLUMNAS(9) <> 0 Then
            .List(.ListCount - 1, 6) = "CANT."
        End If
        If ARR_COLUMNAS(10) <> 0 Then
            .List(.ListCount - 1, 7) = "AUTOR"
        End If
        If ARR_COLUMNAS(8) <> 0 Then
            .List(.ListCount - 1, 8) = "MATERIAL"
        End If
    End With

ElseIf BOOL_MAT_PRIM = True Then

    GRUPO_MAT_ANCHO = 200
    PROD_SEMI_ANCHO = 150
    DES_MAT_ANCHO = 146
    NRO_PARTE_MATERIAL_ANCHO = 120
    ESTADO_TERMIC_ANCHO = 80
    NORM_MAT_PRIM_ANCHO = 80
    APLICACION_ANCHO = 180
    NDP_ANCHO = 90

    STR_WIDTH = GRUPO_MAT_ANCHO & ";" & PROD_SEMI_ANCHO & ";" & DES_MAT_ANCHO & ";" & NRO_PARTE_MATERIAL_ANCHO & ";" & _
    ESTADO_TERMIC_ANCHO & ";" & NORM_MAT_PRIM_ANCHO & ";" & APLICACION_ANCHO & ";" & NDP_ANCHO

    ListBox1.ColumnWidths = STR_WIDTH
    ListBox1.Width = UserForm9.Width - 26
    ListBox1.ColumnCount = 8
    'Populate the listbox.
    With Me.ListBox1
        For i = 2 To UBound(Matriz, 1)
            .AddItem Matriz(i, 1) 'GRUPO_MAT
            .List(.ListCount - 1, 1) = Matriz(i, 2) 'PROD_SEMI
            .List(.ListCount - 1, 2) = Matriz(i, 3) 'DES_MAT
            .List(.ListCount - 1, 3) = Matriz(i, 4) 'NRO_PARTE
            .List(.ListCount - 1, 4) = Matriz(i, 5) 'ESTADO_TERMIC
            .List(.ListCount - 1, 5) = Matriz(i, 6) 'NORM_MAT_PRIM
            .List(.ListCount - 1, 6) = Matriz(i, 12) 'APLICACION
            .List(.ListCount - 1, 7) = Matriz(i, 13) 'NDP
        Next i
    End With
    
    
    ListBox2.ColumnWidths = ListBox1.ColumnWidths
    ListBox2.Width = ListBox1.Width
    ListBox2.ColumnCount = 8
    'Populate the listbox.
    With Me.ListBox2
            .AddItem "GRUPO"
            .List(.ListCount - 1, 1) = "SEMI-ELABORADO"
            .List(.ListCount - 1, 2) = "DESIGNACIÓN"
            .List(.ListCount - 1, 3) = "NRO. DE PARTE"
            .List(.ListCount - 1, 4) = "ESTADO"
            .List(.ListCount - 1, 5) = "NORMA MAT. PRIMA"
            .List(.ListCount - 1, 6) = "APLICACIÓN"
            .List(.ListCount - 1, 7) = "NDP"
    End With

End If

End Sub

Private Sub Lectura(Matriz, PROY_CODE)

ComboBox1.Value = PROY_CODE

TextBox1.BackColor = &H80000004
Label1.Caption = ""
TextBox2.BackColor = &H80000004
Label2.Caption = ""
TextBox3.BackColor = &H80000004
Label3.Caption = ""
TextBox4.BackColor = &H80000004
Label4.Caption = ""
TextBox5.BackColor = &H80000004
Label5.Caption = ""
TextBox9.BackColor = &H80000004
Label9.Caption = ""


Set OBJXL = Nothing

Set OBJXL = CreateObject("Excel.Application")

Call Rutas("ESTRUCTURA", RUTA_SALIDA, PROY_CODE)
Datei = RUTA_SALIDA

Label10.Caption = RUTA_SALIDA

OBJXL.Workbooks.Open FileName:=Datei, ReadOnly:=True
OBJXL.Visible = False
OBJXL.ActiveSheet.Activate

Call Columnas_EP(ARR_COLUMNAS, COL_LIMITE, PROY_CODE)

iCol = COL_LIMITE
Dim a As Long
Dim b As Long
a = iCol
ConvertToLetter = ""
Do While iCol > 0
   a = Int((iCol - 1) / 26)
   b = (iCol - 1) Mod 26
   ConvertToLetter = Chr(b + 65) & ConvertToLetter
   iCol = a
Loop

PN_COSO = OBJXL.Worksheets(1).Range("A1:" & ConvertToLetter & "3000")

AUX_EXCEL = Split(RUTA_SALIDA, "\")
OBJXL.Workbooks(AUX_EXCEL(UBound(AUX_EXCEL))).Close SaveChanges:=False

Set OBJXL = Nothing

End Sub

Attribute VB_Name = "UserForm91"
Attribute VB_Base = "0{95D28A76-A8E1-4DEC-B22A-C6CBEF2FD256}{36845362-233C-46F9-9F30-06A75546D5AE}"
Attribute VB_GlobalNameSpace = False
Attribute VB_Creatable = False
Attribute VB_PredeclaredId = True
Attribute VB_Exposed = False
Attribute VB_TemplateDerived = False
Attribute VB_Customizable = False

Dim Matriz_PARAM(100, 50) As Variant
Dim PARAM_TIP_PART_FILT(50, 2) As Variant
Dim FILTRO As Boolean

Private Sub ComboBox1_Change()

TextBox1.Value = Matriz_PARAM(ComboBox1.ListIndex + 33, 0) & "-" & Matriz_PARAM(ComboBox1.ListIndex + 33, 1)

If ComboBox1.Value <> "" Then
    FILTRO = True
    ComboBox2.Clear
    TextBox2.Value = ""
    it = 0
    For i = 2 To 50
        If Matriz_PARAM(ComboBox1.ListIndex + 33, i) <> "" And Matriz_PARAM(ComboBox1.ListIndex + 33, i) <> 0 Then
            If Matriz_PARAM(32, i) <> "" Then
                it = it + 1
                ComboBox2.AddItem Matriz_PARAM(32, i)
                PARAM_TIP_PART_FILT(it, 1) = Matriz_PARAM(31, i)
                PARAM_TIP_PART_FILT(it, 2) = Matriz_PARAM(ComboBox1.ListIndex + 33, i)
            End If
        End If
    Next
End If


End Sub

Private Sub ComboBox2_Change()

If FILTRO = False Then
    TextBox2.Value = Matriz_PARAM(31, ComboBox2.ListIndex + 3)
Else
    TextBox2.Value = PARAM_TIP_PART_FILT(ComboBox2.ListIndex + 1, 1)
    
    If PARAM_TIP_PART_FILT(ComboBox2.ListIndex + 1, 2) <> "1" Then
        TextBox14.Text = PARAM_TIP_PART_FILT(ComboBox2.ListIndex + 1, 2)
    Else
        TextBox14.Text = ""
    End If
    
End If

End Sub

Private Sub ComboBox3_Change()

TextBox3.Value = Matriz_PARAM(ComboBox3.ListIndex + 2, 2)

End Sub

Private Sub ComboBox4_Change()

TextBox4.Value = Matriz_PARAM(ComboBox4.ListIndex + 2, 4)

End Sub

Private Sub CommandButton1_Click()

'SI SE HABIA ANUNCIADO QUE LA CARGA ES MATERIA PRIMA SE EVITA CHEQUEAR LOS PARÁMETROS CORRESPONDIENTES A TECNOLOGÍA DE FABRICACIÓN Y TIPO DE MATERIAL
If BOOL_MAT_PRIM = False Then
    
    If TextBox1 <> "" And TextBox2 <> "" And TextBox3 <> "" And TextBox4 <> "" Then
        
        STR_TEC = TextBox1.Value
        STR_TIP = TextBox2.Value
        STR_TIP_MAT = TextBox3.Value
        STR_OBD = TextBox4.Value
        
        BOOL_ANCHO = CheckBox2.Value
        BOOL_LARGO = CheckBox3.Value
        BOOL_ESPES = CheckBox4.Value
        BOOL_DIAM = CheckBox5.Value
    
        
        If CheckBox4.Caption = "ALTO" Then
            STR_ANCHO = "Alto"
        Else
            STR_ANCHO = "Espesor"
        End If
        
        STR_DES_MAT = TextBox9.Value
        STR_NRO_PARTE_MAT = TextBox13.Value
        STR_ESTADO_TERMIC = TextBox11.Value
        STR_ESTADO_INI = TextBox12.Value
        STR_NORM_MAT_PRIM = TextBox10.Value
        
        NO_CREAR = False

    Else
        MsgBox "Debe completar todos los campos correspondientes Tecnologia y Material para continuar.", vbExclamation
    End If

ElseIf BOOL_MAT_PRIM = True Then

    'SI SE DETECTA QUE HAY TECNOLOGÍA CARGADA SE ASUME QUE NO SE ESTA CARGANDO SOLO UNA MATERIA PRIMA, SINO UN NUMERO DE PARTE.
    If TextBox1 <> "" And TextBox2 <> "" And TextBox3 <> "" And TextBox4 <> "" Then
        BOOL_MAT_PRIM = False
    End If

    STR_TEC = TextBox1.Value
    STR_TIP = TextBox2.Value
    STR_TIP_MAT = TextBox3.Value
    STR_OBD = TextBox4.Value
    BOOL_ANCHO = CheckBox2.Value
    BOOL_LARGO = CheckBox3.Value
    BOOL_ESPES = CheckBox4.Value
    BOOL_DIAM = CheckBox5.Value
    
    If CheckBox4.Caption = "ALTO" Then
        STR_ANCHO = "Alto"
    Else
        STR_ANCHO = "Espesor"
    End If
    
    STR_DES_MAT = TextBox9.Value
    STR_NRO_PARTE_MAT = TextBox13.Value
    STR_ESTADO_TERMIC = TextBox11.Value
    STR_ESTADO_INI = TextBox12.Value
    STR_NORM_MAT_PRIM = TextBox10.Value
    
    'SI RPREVIAMENTE DETECTO QUE ES MATERIA PRIMA
    If BOOL_MAT_PRIM = True Then
        STR_PN = STR_NRO_PARTE_MAT
    End If
    
    NO_CREAR = False
    

End If

Unload UserForm91

End Sub

Private Sub CommandButton2_Click()

    NO_CREAR = True
    Unload UserForm91

End Sub

Private Sub CommandButton3_Click()

    BOOL_MAT_PRIM = True
    UserForm9.Show

End Sub

Private Sub UserForm_Initialize()

If BOOL_MAT_PRIM = False Then

    ComboBox1.BorderColor = &H8000000D
    ComboBox2.BorderColor = &H8000000D
    ComboBox3.BorderColor = &H8000000D
    ComboBox4.BorderColor = &H8000000D
    ComboBox1.Enabled = True
    ComboBox2.Enabled = True
    ComboBox3.Enabled = True
    ComboBox4.Enabled = True

ElseIf BOOL_MAT_PRIM = True Then

    ComboBox1.BorderColor = &H8000000A
    ComboBox2.BorderColor = &H8000000A
    ComboBox3.BorderColor = &H8000000A
    ComboBox4.BorderColor = &H8000000A
    ComboBox1.Enabled = False
    ComboBox2.Enabled = False
    ComboBox3.Enabled = False
    ComboBox4.Enabled = False

End If

Dim fsDataFile As Object
Dim sText As Object
Dim sPath As String
Dim sFullLine As String

FILTRO = False

'LECTURA DE LOS CÓDIGOS
Call PROYECTO(PROY_CODE, PROYS, ARM_SYS)

'Dim MAT_CODE(1000, 44) As Variant
Call Rutas("PARAMETROS", RUTA_SALIDA, PROY_CODE)

Set fsDataFile = CreateObject("Scripting.FileSystemObject")
'The fully qualified path to your lookup file
sPath = RUTA_SALIDA

'Create a text stream from your FileSystemObject
Set sText = fsDataFile.OpenTextFile(sPath, 1, False)

'Loop through each line in the text stream
j = 0
Do While sText.AtEndOfStream <> True
    linea = linea + 1
    sFullLine = sText.ReadLine
    saCsvData = Split(sFullLine, ";")
    
    j = j + 1
    For i = 0 To UBound(saCsvData)
        Matriz_PARAM(j, i) = saCsvData(i)
    Next
    
Loop

For i = 33 To 60
    If Matriz_PARAM(i, 2) <> "" Then
        ComboBox1.AddItem Matriz_PARAM(i, 2)
    End If
Next

For i = 2 To 50
    If Matriz_PARAM(32, i) <> "" Then
        ComboBox2.AddItem Matriz_PARAM(32, i)
    End If
Next

For i = 1 To 30
    If Matriz_PARAM(i, 3) <> "" Then
        ComboBox3.AddItem Matriz_PARAM(i, 3)
    End If
Next

For i = 1 To 30
    If Matriz_PARAM(i, 5) <> "" Then
        ComboBox4.AddItem Matriz_PARAM(i, 5)
    End If
Next

sText.Close

End Sub
Private Sub CheckBox3_Click()

If CheckBox5.Value = True Then
    If CheckBox3.Value = True Then
        CheckBox4.Value = False
    ElseIf CheckBox3.Value = False Then
        CheckBox4.Value = True
    End If
End If

End Sub

Private Sub CheckBox4_Click()


If CheckBox5.Value = True Then
    If CheckBox4.Value = True Then
        CheckBox3.Value = False
    ElseIf CheckBox4.Value = False Then
        CheckBox3.Value = True
    End If
ElseIf CheckBox5.Value = False Then
    If CheckBox4.Caption <> "ALTO" Then
        CheckBox4.Value = True
        CheckBox4.Caption = "ALTO"
    Else
        CheckBox4.Value = True
        CheckBox4.Caption = "ESPESOR"
    End If
End If

End Sub

Private Sub CheckBox5_Click()

If CheckBox5.Value = True Then
    CheckBox2.Value = False
    CheckBox2.Enabled = False
    CheckBox3.Enabled = True
    CheckBox4.Enabled = True
    CheckBox3.Value = False
    CheckBox4.Value = False
ElseIf CheckBox5.Value = False Then
    CheckBox2.Enabled = False
    CheckBox3.Enabled = False
    CheckBox4.Enabled = True
    CheckBox2.Value = True
    CheckBox3.Value = True
    CheckBox4.Value = True
End If

End Sub

Attribute VB_Name = "UserForm92"
Attribute VB_Base = "0{F42123E3-D6E5-42F1-B6AC-7E7A74449684}{EF64CA28-284B-4943-AB43-7E84FB53D777}"
Attribute VB_GlobalNameSpace = False
Attribute VB_Creatable = False
Attribute VB_PredeclaredId = True
Attribute VB_Exposed = False
Attribute VB_TemplateDerived = False
Attribute VB_Customizable = False


Private Sub CommandButton1_Click()

Unload UserForm92

End Sub

Private Sub TextBox55_Change()

End Sub

Private Sub UserForm_Initialize()

NO_LIBERA = False

If PN_CATIA = PN_RUTA Then
    TextBox53.BackColor = &HFF00&
Else
    NO_LIBERA = True
End If

Label38.Caption = PN_CATIA
Label39.Caption = PN_RUTA

F_CONT = 0

'PUBLICACIÓN
'===========
If BOOL_PARTE = True Then
    If PUB_BODY = "OK" Then
        TextBox55.BackColor = &HFF00&
    Else
        NO_LIBERA = True
    End If
Else
    TextBox55.BackColor = &H80000004
End If

'CSI
'===
If Param_List(1, 2) = "OK" Then
    TextBox1.BackColor = &HFF00&
    If Param_List(1, 3) = "OK" Then
        TextBox27.BackColor = &HFF00&
    Else
        NO_LIBERA = True
    End If
End If

'PRODUCCIÓN
'==========
If Param_List(2, 2) = "OK" Then
    TextBox2.BackColor = &HFF00&
    If Param_List(2, 3) = "OK" Then
        TextBox28.BackColor = &HFF00&
    Else
        NO_LIBERA = True
    End If
End If

If BOOL_PARTE = True Then
    
    'TIPO DE PIEZA
    If Param_List(3, 2) = "OK" Then
        TextBox3.BackColor = &HFF00&
        If Param_List(3, 3) = "OK" Then
            TextBox29.BackColor = &HFF00&
        Else
            NO_LIBERA = True
        End If
    End If
    
    'TECNOLOGIA Y SUBTECNOLOGIA
    If Param_List(4, 2) = "OK" Then
        TextBox4.BackColor = &HFF00&
        If Param_List(4, 3) = "OK" Then
            TextBox30.BackColor = &HFF00&
        Else
            NO_LIBERA = True
        End If
    End If
    
    'OBTENIDO DE
    If Param_List(5, 2) = "OK" Then
        TextBox5.BackColor = &HFF00&
        If Param_List(5, 3) = "OK" Then
            TextBox31.BackColor = &HFF00&
        Else
            NO_LIBERA = True
        End If
    End If
    
    'TIPO DE MATERIAL
    If Param_List(6, 2) = "OK" Then
        TextBox6.BackColor = &HFF00&
        If Param_List(6, 3) = "OK" Then
            TextBox32.BackColor = &HFF00&
        Else
            NO_LIBERA = True
        End If
    End If
    
    If Param_List(4, 4) <> "20-1" Then
        'DESIGNACION MATERIA PRIMA
        If Param_List(7, 2) = "OK" Then
            TextBox7.BackColor = &HFF00&
            If Param_List(7, 3) = "OK" Then
                TextBox33.BackColor = &HFF00&
            Else
                NO_LIBERA = True
            End If
        End If
        
        'NORMA MATERIA PRIMA
        If Param_List(8, 2) = "OK" Then
            TextBox8.BackColor = &HFF00&
            If Param_List(8, 3) = "OK" Then
                TextBox34.BackColor = &HFF00&
            Else
                NO_LIBERA = True
            End If
        End If
        
        'ESTADO INICIAL MATERIA PRIMA (SE PERMITE LIBERAR SIN ESTE PARÁMETRO)
        If Param_List(9, 2) = "OK" Then
            TextBox9.BackColor = &HFF00&
            If Param_List(9, 3) = "OK" Then
                TextBox35.BackColor = &HFF00&
            Else
                'NO_LIBERA = True
            End If
        End If
        
        'ESTADO FINAL MATERIA PRIMA (SE PERMITE LIBERAR SIN ESTE PARÁMETRO)
        If Param_List(10, 2) = "OK" Then
            TextBox10.BackColor = &HFF00&
            If Param_List(10, 3) = "OK" Then
                TextBox36.BackColor = &HFF00&
            Else
                'NO_LIBERA = True
            End If
        End If
    Else
        TextBox7.BackColor = &H80000004
        TextBox33.BackColor = &H80000004
        TextBox8.BackColor = &H80000004
        TextBox34.BackColor = &H80000004
        TextBox9.BackColor = &H80000004
        TextBox35.BackColor = &H80000004
        TextBox10.BackColor = &H80000004
        TextBox36.BackColor = &H80000004
    End If 'Param_List(4, 4) <> "20-1"
    
    'PROTECCION SUPERFICIAL
    If Param_List(25, 2) = "OK" Then
        TextBox25.BackColor = &HFF00&
        If Param_List(25, 3) = "OK" Then
            TextBox51.BackColor = &HFF00&
        Else
            NO_LIBERA = True
        End If
    End If
Else
    TextBox3.BackColor = &H80000004
    TextBox29.BackColor = &H80000004
    TextBox4.BackColor = &H80000004
    TextBox30.BackColor = &H80000004
    TextBox5.BackColor = &H80000004
    TextBox31.BackColor = &H80000004
    TextBox6.BackColor = &H80000004
    TextBox32.BackColor = &H80000004
    TextBox7.BackColor = &H80000004
    TextBox33.BackColor = &H80000004
    TextBox8.BackColor = &H80000004
    TextBox34.BackColor = &H80000004
    TextBox9.BackColor = &H80000004
    TextBox35.BackColor = &H80000004
    TextBox10.BackColor = &H80000004
    TextBox36.BackColor = &H80000004
    TextBox25.BackColor = &H80000004
    TextBox51.BackColor = &H80000004
End If

'MASA
'====
If Param_List(11, 2) = "OK" Then
    TextBox11.BackColor = &HFF00&
    If Param_List(11, 3) = "OK" Then
        TextBox37.BackColor = &HFF00&
    Else
        NO_LIBERA = True
    End If
End If

'PARAMETROS BÁSICOS
'==================

If BOOL_PARTE = True And Param_List(4, 4) <> "20-1" Then
    CONT_DIM = 0

    'ANCHO
    If Param_List(12, 2) = "OK" Then
        CONT_DIM = CONT_DIM + 1
        TextBox12.BackColor = &HFF00&
        If Param_List(12, 3) = "OK" Then
            TextBox38.BackColor = &HFF00&
        Else
            NO_LIBERA = True
        End If
    End If
    
    'LARGO
    If Param_List(13, 2) = "OK" Then
        CONT_DIM = CONT_DIM + 1
        TextBox13.BackColor = &HFF00&
        If Param_List(13, 3) = "OK" Then
            TextBox39.BackColor = &HFF00&
        Else
            NO_LIBERA = True
        End If
    End If
    
    'ALTO
    If Param_List(14, 2) = "OK" Then
        CONT_DIM = CONT_DIM + 1
        TextBox14.BackColor = &HFF00&
        TextBox15.BackColor = &H80000004
        TextBox41.BackColor = &H80000004
        If Param_List(14, 3) = "OK" Then
            TextBox40.BackColor = &HFF00&
        Else
            NO_LIBERA = True
        End If
    End If
    
    'ESPESOR
    If Param_List(15, 2) = "OK" Then
        CONT_DIM = CONT_DIM + 1
        TextBox15.BackColor = &HFF00&
        TextBox14.BackColor = &H80000004
        TextBox40.BackColor = &H80000004
        If Param_List(15, 3) = "OK" Then
            TextBox41.BackColor = &HFF00&
        Else
            NO_LIBERA = True
        End If
    End If
    
    'DIÁMETRO
    If CONT_DIM = 3 Then
        TextBox16.BackColor = &H80000004
        TextBox42.BackColor = &H80000004
    Else
        If Param_List(16, 2) = "OK" Then
            TextBox16.BackColor = &HFF00&
            If Param_List(16, 3) = "OK" Then
                TextBox42.BackColor = &HFF00&
            Else
                NO_LIBERA = True
            End If
        End If
    End If
Else
    TextBox12.BackColor = &H80000004
    TextBox38.BackColor = &H80000004
    TextBox13.BackColor = &H80000004
    TextBox39.BackColor = &H80000004
    TextBox15.BackColor = &H80000004
    TextBox41.BackColor = &H80000004
    TextBox14.BackColor = &H80000004
    TextBox40.BackColor = &H80000004
    TextBox16.BackColor = &H80000004
    TextBox42.BackColor = &H80000004
End If

'MODIFICACIONES
'==============
'IMI
If Param_List(17, 2) = "OK" Then
    TextBox17.BackColor = &HFF00&
    If Param_List(17, 3) = "OK" Then
        TextBox43.BackColor = &HFF00&
    Else
        NO_LIBERA = True
    End If
Else
    NO_LIBERA = True
End If

'FECHA
If Param_List(18, 2) = "OK" Then
    TextBox18.BackColor = &HFF00&
    If Param_List(18, 3) = "OK" Then
        TextBox44.BackColor = &HFF00&
    Else
        NO_LIBERA = True
    End If
Else
    NO_LIBERA = True
End If

'EL PRIMER REVISOR LIBERADOR SE LO CONSIDERA AL AUTOR
If Right(Param_List(17, 1), 1) <> "A" Then
    If Param_List(19, 2) = "OK" Then
        TextBox19.BackColor = &HFF00&
        If Param_List(19, 3) = "OK" Then
            TextBox45.BackColor = &HFF00&
        Else
            NO_LIBERA = True
        End If
    Else
        NO_LIBERA = True
    End If
Else
    TextBox19.BackColor = &H80000004
    TextBox45.BackColor = &H80000004
End If

'REVISORES
'=========
If Param_List(20, 2) = "OK" Then
    TextBox20.BackColor = &HFF00&
    If Param_List(20, 3) = "OK" Then
        TextBox46.BackColor = &HFF00&
    Else
        NO_LIBERA = True
    End If
End If
If Param_List(21, 2) = "OK" Then
    TextBox21.BackColor = &HFF00&
    If Param_List(21, 3) = "OK" Then
        TextBox47.BackColor = &HFF00&
    Else
        NO_LIBERA = True
    End If
End If
If Param_List(22, 2) = "OK" Then
    TextBox22.BackColor = &HFF00&
    If Param_List(22, 3) = "OK" Then
        TextBox48.BackColor = &HFF00&
    Else
        NO_LIBERA = True
    End If
End If
If Param_List(23, 2) = "OK" Then
    TextBox23.BackColor = &HFF00&
        If Param_List(23, 3) = "OK" Then
        TextBox49.BackColor = &HFF00&
    Else
        NO_LIBERA = True
    End If
End If
If Param_List(24, 2) = "OK" Then
    TextBox24.BackColor = &HFF00&
    If Param_List(24, 3) = "OK" Then
        TextBox50.BackColor = &HFF00&
    Else
        NO_LIBERA = True
    End If
End If



If Param_List(26, 2) = "OK" Then
    TextBox26.BackColor = &HFF00&
    If Param_List(26, 3) = "OK" Then
        TextBox52.BackColor = &HFF00&
    Else
        NO_LIBERA = True
    End If
End If

End Sub
