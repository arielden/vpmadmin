Attribute VB_Name = "test_01"
'Display the file path name in a message box.
Sub filepath()
    Dim doc1 As Document
    Set doc1 = CATIA.ActiveDocument
    MsgBox doc1.fullname
End Sub
Sub fullname()
    'Display a message box with the full name of the document.
    MsgBox CATIA.ActiveDocument.fullname
    'Displa a message box with the number of selections in the document.
    MsgBox CATIA.ActiveDocument.Selection.Count

End Sub

Sub get_mass()

'Retrieve the selected component
    Dim oSelection As Selection
    Set oSelection = CATIA.ActiveDocument.Selection
    Dim oProduct As AnyObject
    On Error Resume Next
    Set oProduct = oSelection.FindObject("CATIAProduct")
    
    If (Err.Number <> 0) Then
        MsgBox "No selected product"
    Else
        On Error GoTo 0
        
        'Compute the Inertia properties (mass)
        Dim oInertia As AnyObject
        Set oInertia = oProduct.GetTechnologicalObject("Inertia")
        
        'Read the inertia data
        Dim dMass As Double
        dMass = Round(oInertia.Mass, 3)
        Dim dCoordinates(2)
        oInertia.GetCOGPosition dCoordinates
        
        Dim xcg, ycg, zcg As Double
        
        xcg = Round(dCoordinates(0), 5) * 1000 'Round the result, and convert it to milimeters
        ycg = Round(dCoordinates(1), 5) * 1000
        zcg = Round(dCoordinates(2), 5) * 1000
        
        
        'Display the results
        MsgBox oProduct.name & ": Mass = " & CStr(dMass) & "Kg. " _
        & CStr(xcg) & " xcg " & CStr(ycg) & " ycg " & CStr(zcg) & " zcg "
        
    End If

End Sub

Sub test01()

'Retrieve the selected component
    Dim foundObject As AnyObject
    Dim name As String
    
    Dim NewInertia As Inertia
    Dim AMass As Double
    Set foundObject = CATIA.ActiveDocument.Selection.FindObject("CATIAPart")
    AMass = NewInertia.Mass
    MsgBox AMass
    
    
    On Error Resume Next
    Set foundObject = CATIA.ActiveDocument.Selection.FindObject("CATIAPart")
    
    If (Err.Number <> 0) Then
        MsgBox "No selected product"
    Else
        name = foundObject.name
        MsgBox CStr(name)
        On Error GoTo 0
        
        'Compute the Inertia properties (mass)
        
        
        'Read the inertia data
        Dim dMass As Double
        dMass = Round(oInertia.Mass, 3)
        Dim dCoordinates(2)
        oInertia.GetCOGPosition dCoordinates
        
        Dim xcg, ycg, zcg As Double
        
        xcg = Round(dCoordinates(0), 5) * 1000 'Round the result, and convert it to milimeters
        ycg = Round(dCoordinates(1), 5) * 1000
        zcg = Round(dCoordinates(2), 5) * 1000
        
        
        'Display the results
        MsgBox oProduct.name & ": Mass = " & CStr(dMass) & "Kg. " _
        & CStr(xcg) & " xcg " & CStr(ycg) & " ycg " & CStr(zcg) & " zcg "
        
    End If

End Sub
